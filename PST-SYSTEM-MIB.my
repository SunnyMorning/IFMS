--
-- PST-SYSTEM-MIB.my
-- MIB generated by MG-SOFT Visual MIB Builder Version 6.0  Build 88
-- Monday, May 23, 2018 
--

	PST-SYSTEM-MIB DEFINITIONS ::= BEGIN
 
		IMPORTS
			pstGeneric			
				FROM PST-MIB			
			IpAddress, Integer32, OBJECT-TYPE, OBJECT-IDENTITY			
				FROM SNMPv2-SMI;
		
--
-- Node definitions
--

	
		-- 1.3.6.1.4.1.48391.2.1
		pstSystem OBJECT-IDENTITY
			STATUS current
			DESCRIPTION 
				"Description."
			::= { pstGeneric 1 }

		
		-- 1.3.6.1.4.1.48391.2.1.1
		pstSystemBasicManagement OBJECT IDENTIFIER ::= { pstSystem 1 }

		
		-- 1.3.6.1.4.1.48391.2.1.1.1
		devName OBJECT-TYPE
			SYNTAX OCTET STRING (SIZE (32))
			MAX-ACCESS read-write
			STATUS current
			DESCRIPTION
				"Device's name. The total length should be 32 bytes. Default value:IFMS1000."
			::= { pstSystemBasicManagement 1 }

		
		-- 1.3.6.1.4.1.48391.2.1.1.2
		devIpAddr OBJECT-TYPE
			SYNTAX IpAddress
			MAX-ACCESS read-write
			STATUS current
			DESCRIPTION
				"Device's Ip address. Default value:192.168.1.2."
			::= { pstSystemBasicManagement 2 }

		
		-- 1.3.6.1.4.1.48391.2.1.1.3
		devGateway OBJECT-TYPE
			SYNTAX IpAddress
			MAX-ACCESS read-write
			STATUS current
			DESCRIPTION
				"Device's gateway address. Default value:192.168.1.1."
			::= { pstSystemBasicManagement 3 }

		
		-- 1.3.6.1.4.1.48391.2.1.1.4
		devNetMask OBJECT-TYPE
			SYNTAX IpAddress
			MAX-ACCESS read-write
			STATUS current
			DESCRIPTION
				"Device's netmask value. Default value:255.255.255.0."
			::= { pstSystemBasicManagement 4 }

		
		-- 1.3.6.1.4.1.48391.2.1.1.5
		saveCurrentConfiguration OBJECT-TYPE
			SYNTAX Integer32 (1)
			MAX-ACCESS read-write
			STATUS current
			DESCRIPTION
				"Description."
			::= { pstSystemBasicManagement 5 }

		
		-- 1.3.6.1.4.1.48391.2.1.1.6
		reset2Factory OBJECT-TYPE
			SYNTAX Integer32 (1)
			MAX-ACCESS read-write
			STATUS current
			DESCRIPTION
				"Write value 1 will reset device to default factory configuration."
			::= { pstSystemBasicManagement 6 }

		
		-- 1.3.6.1.4.1.48391.2.1.1.7
		reboot OBJECT-TYPE
			SYNTAX Integer32
			MAX-ACCESS read-write
			STATUS current
			DESCRIPTION
				"1. Warm reset
				 2. Cold reset"
			::= { pstSystemBasicManagement 7 }

		-- 1.3.6.1.4.1.48391.2.1.1.8
		DDRConsumption OBJECT-TYPE
			SYNTAX Integer32    
			UNITS "%"
			MAX-ACCESS read-only
			STATUS current
			DESCRIPTION
				"Percentage of DDR consumption, %"
			::= { pstSystemBasicManagement 8 } 
			
		-- 1.3.6.1.4.1.48391.2.1.1.9
		DDRCleanUp OBJECT-TYPE
			SYNTAX Integer32    
			MAX-ACCESS read-write
			STATUS current
			DESCRIPTION
				"Write value 1 clean up DDR."
			::= { pstSystemBasicManagement 9 }        
						
			
		
		-- 1.3.6.1.4.1.48391.2.1.2
		pstSystemVerInfo OBJECT IDENTIFIER ::= { pstSystem 2 }

		
-- The hardware version of the device.
		-- 1.3.6.1.4.1.48391.2.1.2.1
		pstHwVer OBJECT-TYPE
			SYNTAX OCTET STRING (SIZE (32))
			MAX-ACCESS read-only
			STATUS current
			DESCRIPTION
				"Default value:1.0.0."
			::= { pstSystemVerInfo 1 }

		
-- The software version of the device.
		-- 1.3.6.1.4.1.48391.2.1.2.2
		pstSwVer OBJECT-TYPE
			SYNTAX OCTET STRING (SIZE (32))
			MAX-ACCESS read-only
			STATUS current
			DESCRIPTION
				"Default value:1.0.0."
			::= { pstSystemVerInfo 2 }

		
-- The firmware version of the device.
		-- 1.3.6.1.4.1.48391.2.1.2.3
		pstFwVer OBJECT-TYPE
			SYNTAX OCTET STRING (SIZE (32))
			MAX-ACCESS read-only
			STATUS current
			DESCRIPTION
				"Default value:1.0.0."
			::= { pstSystemVerInfo 3 }

		
-- The part number of the device.
		-- 1.3.6.1.4.1.48391.2.1.2.4
		pstModel OBJECT-TYPE
			SYNTAX OCTET STRING (SIZE (32))
			MAX-ACCESS read-only
			STATUS current
			DESCRIPTION
				"Default value:IFMS1000."
			::= { pstSystemVerInfo 4 }

		
-- The serial number of the device.
		-- 1.3.6.1.4.1.48391.2.1.2.5
		pstSn OBJECT-TYPE
			SYNTAX OCTET STRING (SIZE (32))
			MAX-ACCESS read-write
			STATUS current
			DESCRIPTION
				"Default value:201806010001."
			::= { pstSystemVerInfo 5 }

		
-- Mac Address of the device. For example, 00:01:02:03:04:05
		-- 1.3.6.1.4.1.48391.2.1.2.6
		devMacAddress OBJECT-TYPE
			SYNTAX OCTET STRING (SIZE (17))
			MAX-ACCESS read-only
			STATUS current
			DESCRIPTION
				"Description."
			::= { pstSystemVerInfo 6 }

		
		-- 1.3.6.1.4.1.48391.2.1.3
		pstSystemTrapInfo OBJECT IDENTIFIER ::= { pstSystem 3 }

		
		-- 1.3.6.1.4.1.48391.2.1.3.1
		pstSystemTrapFuncEn OBJECT-TYPE
			SYNTAX Integer32 (0..1)
			MAX-ACCESS read-write
			STATUS current
			DESCRIPTION
				"Enable/Disable trap function.
				0: Disable.
				1: Enable."
			DEFVAL { 0 }
			::= { pstSystemTrapInfo 1 }

		
		-- 1.3.6.1.4.1.48391.2.1.3.2
		pstSystemTrapTargetTable OBJECT-TYPE
			SYNTAX SEQUENCE OF PSTSystemTrapTargetEntry
			MAX-ACCESS not-accessible
			STATUS current
			DESCRIPTION
				"Description."
			::= { pstSystemTrapInfo 2 }

		
		-- 1.3.6.1.4.1.48391.2.1.3.2.1
		pstSystemTrapTargetEntry OBJECT-TYPE
			SYNTAX PSTSystemTrapTargetEntry
			MAX-ACCESS not-accessible
			STATUS current
			DESCRIPTION
				"Description."
			INDEX { pstSystemTrapTargetName }
			::= { pstSystemTrapTargetTable 1 }

		
		PSTSystemTrapTargetEntry ::=
			SEQUENCE { 
				pstSystemTrapTargetName
					Integer32,
				pstSystemTrapTargetIpAddr
					OCTET STRING,
				pstSystemTrapTargetCommunity
					OCTET STRING,
				pstSystemTrapTargetTrapVersion
					Integer32,
				pstSystemTrapTargetRowStatus
					INTEGER
			 }

		-- 1.3.6.1.4.1.48391.2.1.3.2.1.1
		pstSystemTrapTargetName OBJECT-TYPE
			SYNTAX Integer32 (1..8)
			MAX-ACCESS not-accessible
			STATUS current
			DESCRIPTION
				"Description."
			::= { pstSystemTrapTargetEntry 1 }

		
		-- 1.3.6.1.4.1.48391.2.1.3.2.1.2
		pstSystemTrapTargetIpAddr OBJECT-TYPE
			SYNTAX OCTET STRING (SIZE (1..32))
			MAX-ACCESS read-write
			STATUS current
			DESCRIPTION
				"Input the target's IP address you want to send trap. Default value:192.168.1.44."
			::= { pstSystemTrapTargetEntry 2 }

		
		-- 1.3.6.1.4.1.48391.2.1.3.2.1.3
		pstSystemTrapTargetCommunity OBJECT-TYPE
			SYNTAX OCTET STRING (SIZE (1..32))
			MAX-ACCESS read-write
			STATUS current
			DESCRIPTION
				"The community name you want to send with the trap. Default value:Public."
			::= { pstSystemTrapTargetEntry 3 }

		
		-- 1.3.6.1.4.1.48391.2.1.3.2.1.4
		pstSystemTrapTargetTrapVersion OBJECT-TYPE
			SYNTAX Integer32 (0..1)
			MAX-ACCESS read-write
			STATUS current
			DESCRIPTION
				"0: Trap V1
				1: Trap V2
				2: Trap V1 and Trap V2"
			::= { pstSystemTrapTargetEntry 4 }

		
		-- 1.3.6.1.4.1.48391.2.1.3.2.1.5
		pstSystemTrapTargetRowStatus OBJECT-TYPE
			SYNTAX INTEGER
			MAX-ACCESS read-create
			STATUS current
			DESCRIPTION
				"The status of this conceptual row.	
				To create a row in this table, a manager must set this object to either createAndGo(4) or createAndWait(5)."
			::= { pstSystemTrapTargetEntry 5 }

		
		-- 1.3.6.1.4.1.48391.2.1.4
		pstSystemStatus OBJECT IDENTIFIER ::= { pstSystem 4 }

		
		-- 1.3.6.1.4.1.48391.2.1.4.1
		pstSystemFanTotalNum OBJECT-TYPE
			SYNTAX Integer32
			MAX-ACCESS read-only
			STATUS current
			DESCRIPTION
				"The total number of current device's fans."
			::= { pstSystemStatus 1 }

		
		-- 1.3.6.1.4.1.48391.2.1.4.2
		pstSystemPowerTotalNum OBJECT-TYPE
			SYNTAX Integer32 
			UNITS "W"
			MAX-ACCESS read-only
			STATUS current
			DESCRIPTION
				"The total number of current device's power."
			::= { pstSystemStatus 2 }

		
		-- 1.3.6.1.4.1.48391.2.1.4.3
		pstSystemFanTable OBJECT-TYPE
			SYNTAX SEQUENCE OF PSTSystemFanEntry
			MAX-ACCESS not-accessible
			STATUS current
			DESCRIPTION
				"Description."
			::= { pstSystemStatus 3 }

		
		-- 1.3.6.1.4.1.48391.2.1.4.3.1
		pstSystemFanEntry OBJECT-TYPE
			SYNTAX PSTSystemFanEntry
			MAX-ACCESS not-accessible
			STATUS current
			DESCRIPTION
				"Description."
			INDEX { pstSystemFanIndex }
			::= { pstSystemFanTable 1 }

		
		PSTSystemFanEntry ::=
			SEQUENCE { 
				pstSystemFanIndex
					Integer32,
				pstSystemFanStatus
					Integer32,
				pstSystemFanSpeed
					Integer32
			 }

		-- 1.3.6.1.4.1.48391.2.1.4.3.1.1
		pstSystemFanIndex OBJECT-TYPE
			SYNTAX Integer32
			MAX-ACCESS read-only
			STATUS current
			DESCRIPTION
				"Fan Index. 
				The max value is 'pstSystemFanTotalNum'."
			::= { pstSystemFanEntry 1 }

		
		-- 1.3.6.1.4.1.48391.2.1.4.3.1.2
		pstSystemFanStatus OBJECT-TYPE
			SYNTAX Integer32 (0..1)
			MAX-ACCESS read-only
			STATUS current
			DESCRIPTION
				"Fan's working status.
				0. OK
				1. Fault
				ALERT_0  1,2
				ALERT_1  3,4
				"
			::= { pstSystemFanEntry 2 }

		
		-- 1.3.6.1.4.1.48391.2.1.4.3.1.3
		pstSystemFanSpeed OBJECT-TYPE
			SYNTAX Integer32
			UNITS "R.P.M"
			MAX-ACCESS read-only
			STATUS current
			DESCRIPTION
				"Fan's Speed."
			::= { pstSystemFanEntry 3 }

		
		-- 1.3.6.1.4.1.48391.2.1.4.4
		pstSystemPowerTable OBJECT-TYPE
			SYNTAX SEQUENCE OF PSTSystemPowerEntry
			MAX-ACCESS not-accessible
			STATUS current
			DESCRIPTION
				"Description."
			::= { pstSystemStatus 4 }

		
		-- 1.3.6.1.4.1.48391.2.1.4.4.1
		pstSystemPowerEntry OBJECT-TYPE
			SYNTAX PSTSystemPowerEntry
			MAX-ACCESS not-accessible
			STATUS current
			DESCRIPTION
				"Description."
			INDEX { pstSystemPowerIndex }
			::= { pstSystemPowerTable 1 }

		
		PSTSystemPowerEntry ::=
			SEQUENCE { 
				pstSystemPowerIndex					
					OCTET STRING,
				pstSystemPowerMaximumConsumption					
					OCTET STRING,
				pstSystemPowerVoltage12VA
					OCTET STRING,
				pstSystemPowerVoltage12VB
					OCTET STRING,
				pstSystemPowerVoltage12VFAN
					OCTET STRING,
				pstSystemPowerVoltage12VOTDR1
					OCTET STRING,
				pstSystemPowerVoltage12VOTDR2
					OCTET STRING,
				pstSystemPowerVoltageVDD5V
					OCTET STRING,
				pstSystemPowerVoltageVDD3V3
					OCTET STRING,
				pstSystemPowerVoltage1V8RTC
					OCTET STRING
			 }     
			 

		-- 1.3.6.1.4.1.48391.2.1.4.4.1.1
		pstSystemPowerIndex OBJECT-TYPE
			SYNTAX OCTET STRING (SIZE (1..16)) 
			MAX-ACCESS read-only
			STATUS current
			DESCRIPTION
				"pstSystemPowerIndex."
			::= { pstSystemPowerEntry 1 }
			 

		-- 1.3.6.1.4.1.48391.2.1.4.4.1.2
		pstSystemPowerMaximumConsumption OBJECT-TYPE
			SYNTAX OCTET STRING (SIZE (1..16))  
			UNITS "W"
			MAX-ACCESS read-only
			STATUS current
			DESCRIPTION
				"Maximum power consumption of equipment."
			::= { pstSystemPowerEntry 2 }

		
		-- 1.3.6.1.4.1.48391.2.1.4.4.1.3
		pstSystemPowerVoltage12VA OBJECT-TYPE
			SYNTAX OCTET STRING (SIZE (1..16))
			UNITS "V"
			MAX-ACCESS read-only
			STATUS current
			DESCRIPTION
				"12VA"
			::= { pstSystemPowerEntry 3 }
		
		-- 1.3.6.1.4.1.48391.2.1.4.4.1.4
		pstSystemPowerVoltage12VB OBJECT-TYPE
			SYNTAX OCTET STRING (SIZE (1..16))
			UNITS "V"
			MAX-ACCESS read-only
			STATUS current
			DESCRIPTION
				"12VB"
			::= { pstSystemPowerEntry 4 }

		
		-- 1.3.6.1.4.1.48391.2.1.4.4.1.5
		pstSystemPowerVoltage12VFAN OBJECT-TYPE
			SYNTAX OCTET STRING (SIZE (1..16))
			UNITS "V"
			MAX-ACCESS read-only
			STATUS current
			DESCRIPTION
				"12VFAN"
			::= { pstSystemPowerEntry 5 }


		-- 1.3.6.1.4.1.48391.2.1.4.4.1.6
		pstSystemPowerVoltage12VOTDR1 OBJECT-TYPE
			SYNTAX OCTET STRING (SIZE (1..16))
			UNITS "V"
			MAX-ACCESS read-only
			STATUS current
			DESCRIPTION
				"12VOTDR1"
			::= { pstSystemPowerEntry 6 }  
			
			
		-- 1.3.6.1.4.1.48391.2.1.4.4.1.7
		pstSystemPowerVoltage12VOTDR2 OBJECT-TYPE
			SYNTAX OCTET STRING (SIZE (1..16))
			UNITS "V"
			MAX-ACCESS read-only
			STATUS current
			DESCRIPTION
				"12VOTDR2"
			::= { pstSystemPowerEntry 7 }  			
			

		-- 1.3.6.1.4.1.48391.2.1.4.4.1.8
		pstSystemPowerVoltageVDD5V OBJECT-TYPE
			SYNTAX OCTET STRING (SIZE (1..16))
			UNITS "V"
			MAX-ACCESS read-only
			STATUS current
			DESCRIPTION
				"VDD5V"
			::= { pstSystemPowerEntry 8 } 
			
		-- 1.3.6.1.4.1.48391.2.1.4.4.1.9
		pstSystemPowerVoltageVDD3V3 OBJECT-TYPE
			SYNTAX OCTET STRING (SIZE (1..16))
			UNITS "V"
			MAX-ACCESS read-only
			STATUS current
			DESCRIPTION
				"VDD3V3"
			::= { pstSystemPowerEntry 9 } 			


		-- 1.3.6.1.4.1.48391.2.1.4.4.1.10
		pstSystemPowerVoltage1V8RTC OBJECT-TYPE
			SYNTAX OCTET STRING (SIZE (1..16))
			UNITS "V"
			MAX-ACCESS read-only
			STATUS current
			DESCRIPTION
				"1V8RTC"
			::= { pstSystemPowerEntry 10 } 
			
					
		-- 1.3.6.1.4.1.48391.2.1.4.5
		pstSystemTemperature OBJECT-TYPE
			SYNTAX OCTET STRING (SIZE (1..16))
			UNITS "C"
			MAX-ACCESS read-only
			STATUS current
			DESCRIPTION
				"This device's temperature."
			::= { pstSystemStatus 5 }    
			
			
		-- 1.3.6.1.4.1.48391.2.1.4.6
		pstSystemTemperatureHighThreshold OBJECT-TYPE
			SYNTAX OCTET STRING (SIZE (1..16))
			UNITS "C"
			MAX-ACCESS read-write
			STATUS current
			DESCRIPTION
				"This device's temperature high threshold."
			::= { pstSystemStatus 6 }


		-- 1.3.6.1.4.1.48391.2.1.4.7
		pstSystemTemperatureLowThreshold OBJECT-TYPE
			SYNTAX OCTET STRING (SIZE (1..16))
			UNITS "C"
			MAX-ACCESS read-write
			STATUS current
			DESCRIPTION
				"This device's temperature low threshold."
			::= { pstSystemStatus 7 }
                                            
 		-- 1.3.6.1.4.1.48391.2.1.4.8
		pstSystemTemperatureControlMode OBJECT-TYPE
			SYNTAX Integer32
			MAX-ACCESS read-write
			STATUS current
			DESCRIPTION
				"1.Full speed mode 
				 2.Auto control mode"
			::= { pstSystemStatus 8 }       
			

		-- 1.3.6.1.4.1.48391.2.1.4.9
		pstSystemADG707Switch OBJECT-TYPE
			SYNTAX Integer32 (1..8)
			MAX-ACCESS read-write
			STATUS current
			DESCRIPTION
				"1. 
				 2.
				 3.OTDR2
				 4.OTDR1
				 5.Swtich Console
				 6.UART1
				 7.UART0
				 8.UART0"
			::= { pstSystemStatus 9 }

                                         
                                                                                                                           		
		-- 1.3.6.1.4.1.48391.2.1.5
		pstSystemOnlineUpgrade OBJECT IDENTIFIER ::= { pstSystem 5 }

		
		-- 1.3.6.1.4.1.48391.2.1.5.1
		pstSystemFtpSrvIp OBJECT-TYPE
			SYNTAX IpAddress
			MAX-ACCESS read-write
			STATUS current
			DESCRIPTION
				"FTP server's IP address."
			::= { pstSystemOnlineUpgrade 1 }

		
		-- 1.3.6.1.4.1.48391.2.1.5.2
		pstSystemFtpUserName OBJECT-TYPE
			SYNTAX OCTET STRING (SIZE (1..16))
			MAX-ACCESS read-write
			STATUS current
			DESCRIPTION
				"The user name of FTP server. "
			::= { pstSystemOnlineUpgrade 2 }

		
		-- 1.3.6.1.4.1.48391.2.1.5.3
		pstSystemFtpUserPwd OBJECT-TYPE
			SYNTAX OCTET STRING (SIZE (1..16))
			MAX-ACCESS read-write
			STATUS current
			DESCRIPTION
				"The user password of FTP server. "
			::= { pstSystemOnlineUpgrade 3 }

		
		-- 1.3.6.1.4.1.48391.2.1.5.4
		pstSystemFtpFileName OBJECT-TYPE
			SYNTAX OCTET STRING (SIZE (1..64))
			MAX-ACCESS read-write
			STATUS current
			DESCRIPTION
				"The file's name which should be got from FTP server. "
			::= { pstSystemOnlineUpgrade 4 }

		
		-- 1.3.6.1.4.1.48391.2.1.5.5
		pstSystemUpgFileType OBJECT-TYPE
			SYNTAX Integer32 (1..3)
			MAX-ACCESS read-write
			STATUS current
			DESCRIPTION
				"The file's type for upgrade.
				1. Software Image.
				2. Firmware Image.
				3. Configuration File."
			::= { pstSystemOnlineUpgrade 5 }

		
		-- 1.3.6.1.4.1.48391.2.1.5.6
		pstSystemUpgDstSlot OBJECT-TYPE
			SYNTAX Integer32
			MAX-ACCESS read-write
			STATUS current
			DESCRIPTION
				"The destination slot number which you want to upgrade."
			::= { pstSystemOnlineUpgrade 6 }

		
		-- 1.3.6.1.4.1.48391.2.1.5.7
		pstSystemUpgAction OBJECT-TYPE
			SYNTAX Integer32 (1..2)
			MAX-ACCESS read-write
			STATUS current
			DESCRIPTION
				"Start ftp action.
				1. Start downloading from FTP server.
				2. Start uploading to FTP server."
			::= { pstSystemOnlineUpgrade 7 }

		
		-- 1.3.6.1.4.1.48391.2.1.5.8
		pstSystemUpgStatus OBJECT-TYPE
			SYNTAX Integer32 (0..3)
			MAX-ACCESS read-only
			STATUS current
			DESCRIPTION
				"The upgrade status.
				0. Ready to upgrade.
				1. Upgrading.
				2. Upgrade successfully.
				3. Upgrade failed."
			::= { pstSystemOnlineUpgrade 8 }

		
		-- 1.3.6.1.4.1.48391.2.1.5.9
		pstSystemUpgResultInfo OBJECT-TYPE
			SYNTAX OCTET STRING (SIZE (0..64))
			MAX-ACCESS read-only
			STATUS current
			DESCRIPTION
				"Display some information from here when upgrade failed. If upgrade successfully, it should be NULL."
			::= { pstSystemOnlineUpgrade 9 }

		
		-- 1.3.6.1.4.1.48391.2.1.6
		pstSystemProductInfo OBJECT-IDENTITY
			STATUS current
			DESCRIPTION 
				"Description."
			::= { pstSystem 6 }

		
		-- 1.3.6.1.4.1.48391.2.1.6.1
		pstSystemProductType OBJECT-TYPE
			SYNTAX Integer32
			MAX-ACCESS read-only
			STATUS current
			DESCRIPTION
				"Indicates the product's type.
				1. 2060
				2. 3030
				3. 6100
				4. 6200"
			::= { pstSystemProductInfo 1 }

		
	
	END

--
-- PST-SYSTEM-MIB.my
--
