--
-- PST-IFMS1000-MIB.my
-- MIB generated by MG-SOFT Visual MIB Builder Version 6.0  Build 88
-- Monday, May 08, 2017 at 14:17:24
--

	PST-IFMS1000-MIB DEFINITIONS ::= BEGIN
 
		IMPORTS
			pstProducts			
				FROM PST-MIB			
			IpAddress, Integer32, Unsigned32, OBJECT-TYPE, OBJECT-IDENTITY, 
			NOTIFICATION-TYPE			
				FROM SNMPv2-SMI;
	
	
--
-- Node definitions
--
	
		-- 1.3.6.1.4.1.48391.3.5
		pstIFMS1000 OBJECT-IDENTITY
			STATUS current
			DESCRIPTION 
				"Description."
			::= { pstProducts 5 }

		
		-- 1.3.6.1.4.1.48391.3.5.1
		pstIFMS1000PortInfoTable OBJECT-TYPE
			SYNTAX SEQUENCE OF PSTIFMS1000PortInfoEntry
			MAX-ACCESS not-accessible
			STATUS current
			DESCRIPTION
				"Description."
			::= { pstIFMS1000 1 }

		
		-- 1.3.6.1.4.1.48391.3.5.1.1
		pstIFMS1000PortInfoEntry OBJECT-TYPE
			SYNTAX PSTIFMS1000PortInfoEntry
			MAX-ACCESS not-accessible
			STATUS current
			DESCRIPTION
				"Description."
			INDEX { pstIFMS1000PortNum }
			::= { pstIFMS1000PortInfoTable 1 }

		
		PSTIFMS1000PortInfoEntry ::=
			SEQUENCE { 
				pstIFMS1000PortNum
					Integer32,
				pstIFMS1000PortRxPwr
					OCTET STRING,
				pstIFMS1000PortTxPwr
					OCTET STRING,
				pstIFMS1000PortWorkMode
					Integer32,
				pstIFMS1000PortActive
					Integer32,
				pstIFMS1000PortFiberAppType
					Integer32,
				pstIFMS1000PortRunningStatus
					Integer32  

			 }

		-- 1.3.6.1.4.1.48391.3.5.1.1.1
		pstIFMS1000PortNum OBJECT-TYPE
			SYNTAX Integer32 (1..8)
			MAX-ACCESS read-only
			STATUS current
			DESCRIPTION
				"Description."
			::= { pstIFMS1000PortInfoEntry 1 }

		
		-- 1.3.6.1.4.1.48391.3.5.1.1.2
		pstIFMS1000PortRxPwr OBJECT-TYPE
			SYNTAX OCTET STRING (SIZE (1..32))
			UNITS "dBm"
			MAX-ACCESS read-only
			STATUS current
			DESCRIPTION
				"Port Rx Power.
				"
			::= { pstIFMS1000PortInfoEntry 2 }

		
		-- 1.3.6.1.4.1.48391.3.5.1.1.3
		pstIFMS1000PortTxPwr OBJECT-TYPE
			SYNTAX OCTET STRING (SIZE (1..32))
			UNITS "dBm"
			MAX-ACCESS read-only
			STATUS current
			DESCRIPTION
				"Port Tx Power.
				"
			::= { pstIFMS1000PortInfoEntry 3 }

		
		-- 1.3.6.1.4.1.48391.3.5.1.1.4
		pstIFMS1000PortWorkMode OBJECT-TYPE
			SYNTAX Integer32 (1..2)
			MAX-ACCESS read-write
			STATUS current
			DESCRIPTION
				"Indicates which mode the port is working on.
				1. Transmission.
				2. PON"
			::= { pstIFMS1000PortInfoEntry 4 }

		
		-- 1.3.6.1.4.1.48391.3.5.1.1.5
		pstIFMS1000PortActive OBJECT-TYPE
			SYNTAX Integer32 (0..1)
			MAX-ACCESS read-write
			STATUS current
			DESCRIPTION
				"Indicates whether the port is active for work.
				0. Not active
				1. Active."
			::= { pstIFMS1000PortInfoEntry 5 }

		
		-- 1.3.6.1.4.1.48391.3.5.1.1.6
		pstIFMS1000PortFiberAppType OBJECT-TYPE
			SYNTAX Integer32 (1..2)
			MAX-ACCESS read-write
			STATUS current
			DESCRIPTION
				"Indicates which application type the port's fiber is working on.
				1. Dark fiber
				2. Active fiber"
			::= { pstIFMS1000PortInfoEntry 6 }

		
		-- 1.3.6.1.4.1.48391.3.5.1.1.7
		pstIFMS1000PortRunningStatus OBJECT-TYPE
			SYNTAX Integer32 (1..2)
			MAX-ACCESS read-only
			STATUS current
			DESCRIPTION
				"Indicates current port's running status.
				1. Normal
				2. Abnormal"
			::= { pstIFMS1000PortInfoEntry 7 }       
			
		
		-- 1.3.6.1.4.1.48391.3.5.2
		pstIFMS1000MeasureTable OBJECT-TYPE
			SYNTAX SEQUENCE OF PSTIFMS1000MeasureEntry
			MAX-ACCESS not-accessible
			STATUS current
			DESCRIPTION
				"Description."
			::= { pstIFMS1000 2 }

		
		-- 1.3.6.1.4.1.48391.3.5.2.1
		pstIFMS1000MeasureEntry OBJECT-TYPE
			SYNTAX PSTIFMS1000MeasureEntry
			MAX-ACCESS not-accessible
			STATUS current
			DESCRIPTION
				"Description."
			INDEX { pstIFMS1000MTPortNum }
			::= { pstIFMS1000MeasureTable 1 }

		
		PSTIFMS1000MeasureEntry ::=
			SEQUENCE { 
				pstIFMS1000MTPortNum
					Integer32,
				pstIFMS1000MeasureStartPosition
					OCTET STRING,
				pstIFMS1000MeasureEndPosition
					OCTET STRING,
				pstIFMS1000MeasureRefIndex
					OCTET STRING,
				pstIFMS1000MeasureResolution
					OCTET STRING,
				pstIFMS1000MeasureStatus
					Integer32,
				pstIFMS1000MeasureAction
					Integer32,
				pstIFMS1000MeasurePulseWidth
					OCTET STRING,
				pstIFMS1000MeasureMeasureTime
					Integer32,
				pstIFMS1000MeasureProgressStatus
					Integer32,
				pstIFMS1000MeasureTLOS
					OCTET STRING,  
				pstIFMS1000MeasureTREF
					OCTET STRING,
				pstIFMS1000MeasureFiberLengthChangeThreshold 
					OCTET STRING, 
				pstIFMS1000MeasureEndToEndLossHighThreshold 
					OCTET STRING,										         
				pstIFMS1000MeasureEndToEndLossMiddleThreshold 
					OCTET STRING,	
				pstIFMS1000MeasureEndToEndLossLowThreshold
					OCTET STRING,	
				pstIFMS1000MeasureNewLossCriticalThreshold 
					OCTET STRING,	
				pstIFMS1000MeasureNewLossMajorThreshold 
					OCTET STRING,	
				pstIFMS1000MeasureNewLossMinorThreshold 
					OCTET STRING,	
				pstIFMS1000MeasureOldLossCriticalThreshold 
					OCTET STRING,	
				pstIFMS1000MeasureOldLossMajorThreshold 
					OCTET STRING,	
				pstIFMS1000MeasureOldLossMinorThreshold 
					OCTET STRING,	
				pstIFMS1000MeasureEventPositionChangeThreshold 
					OCTET STRING,	
				pstIFMS1000MeasureReserved2 
					OCTET STRING,																					
				pstIFMS1000MeasureNumber 
					OCTET STRING,					
				pstIFMS1000MeasureNumberSORStoredEachChannel 
					OCTET STRING
																										
			 }    
			 

		-- 1.3.6.1.4.1.48391.3.5.2.1.1
		pstIFMS1000MTPortNum OBJECT-TYPE
			SYNTAX Integer32 (1..8)
			MAX-ACCESS read-only
			STATUS current
			DESCRIPTION
				"Description."
			::= { pstIFMS1000MeasureEntry 1 }

		
-- Start position of measurement.
		-- 1.3.6.1.4.1.48391.3.5.2.1.2
		pstIFMS1000MeasureStartPosition OBJECT-TYPE
			SYNTAX OCTET STRING (SIZE (1..32))
			UNITS "Meter"
			MAX-ACCESS read-write
			STATUS current
			DESCRIPTION
				"The start position in the measurement. Default value:0"
			::= { pstIFMS1000MeasureEntry 2 }

		
-- End position of measurement.
		-- 1.3.6.1.4.1.48391.3.5.2.1.3
		pstIFMS1000MeasureEndPosition OBJECT-TYPE
			SYNTAX OCTET STRING (SIZE (1..32))
			UNITS "KiloMeter"
			MAX-ACCESS read-write
			STATUS current
			DESCRIPTION
				"The total length in the measurement.(5,25,50,125,160,260)(km)"
			::= { pstIFMS1000MeasureEntry 3 }

		
		-- 1.3.6.1.4.1.48391.3.5.2.1.4
		pstIFMS1000MeasureRefIndex OBJECT-TYPE
			SYNTAX OCTET STRING (SIZE (1..32))
			MAX-ACCESS read-write
			STATUS current
			DESCRIPTION
				"The refractive index in the measurement. Default value:1.465; Range:1.400~1.700"
			::= { pstIFMS1000MeasureEntry 4 }

		
		-- 1.3.6.1.4.1.48391.3.5.2.1.5
		pstIFMS1000MeasureResolution OBJECT-TYPE
			SYNTAX OCTET STRING (SIZE (1..32))
			UNITS "Meter"
			MAX-ACCESS read-write
			STATUS current
			DESCRIPTION
				"The resolution in the measurement. (0.32,0.64,1.2,2.5,5,10,20)(m)"
			::= { pstIFMS1000MeasureEntry 5 }

		
		-- 1.3.6.1.4.1.48391.3.5.2.1.6
		pstIFMS1000MeasureStatus OBJECT-TYPE
			SYNTAX Integer32
			MAX-ACCESS read-only
			STATUS current
			DESCRIPTION
				"The measurement action.
					0. Idle. The port is idle now. 
					1. Auto measurement is running. 
					2. Single OTDR measurement is running. 
					3. Single OTDR measurement is done. 
					4. Measurement Failure. 
				"
			::= { pstIFMS1000MeasureEntry 6 }

		
		-- 1.3.6.1.4.1.48391.3.5.2.1.7
		pstIFMS1000MeasureAction OBJECT-TYPE
			SYNTAX Integer32
			MAX-ACCESS read-write
			STATUS current
			DESCRIPTION
				"The measurement action.
					1. Start Auto measurement. 				
					2. Stop Auto measurement.
					3. Start Single measurement.
				"
			::= { pstIFMS1000MeasureEntry 7 }

		
		-- 1.3.6.1.4.1.48391.3.5.2.1.8
		pstIFMS1000MeasurePulseWidth OBJECT-TYPE    
			SYNTAX OCTET STRING (SIZE (1..32))
			UNITS "ns"
			MAX-ACCESS read-write
			STATUS current
			DESCRIPTION
				"The pulse width is 10,30,100,300,1000,3000,10000,20000(ns)"
			::= { pstIFMS1000MeasureEntry 8 }

		
		-- 1.3.6.1.4.1.48391.3.5.2.1.9
		pstIFMS1000MeasureTime OBJECT-TYPE
			SYNTAX Integer32
			MAX-ACCESS read-write
			STATUS current
			DESCRIPTION
				"5~300 Second"
			::= { pstIFMS1000MeasureEntry 9 }

		
		-- 1.3.6.1.4.1.48391.3.5.2.1.10
		pstIFMS1000MeasureProgressStatus OBJECT-TYPE
			SYNTAX Integer32 (0..100)
			MAX-ACCESS read-only
			STATUS current
			DESCRIPTION
				"Indicates current measurement's progress status. It is the value of percentage."
			::= { pstIFMS1000MeasureEntry 10 }

		
		-- 1.3.6.1.4.1.48391.3.5.2.1.11
		pstIFMS1000MeasureTLOS OBJECT-TYPE
			SYNTAX OCTET STRING (SIZE (1..32))
			MAX-ACCESS read-write
			STATUS current
			DESCRIPTION
				"The default value is 0(0~9.99), initialization module TLOS."
			::= { pstIFMS1000MeasureEntry 11 }       

			
		-- 1.3.6.1.4.1.48391.3.5.2.1.12
		pstIFMS1000MeasureTREF OBJECT-TYPE
			SYNTAX OCTET STRING (SIZE (1..32))
			MAX-ACCESS read-write
			STATUS current
			DESCRIPTION
				"The default value is -80(-14~-80), initialization module TREF."
			::= { pstIFMS1000MeasureEntry 12 }    

			
		-- 1.3.6.1.4.1.48391.3.5.2.1.13
		pstIFMS1000MeasureFiberLengthChangeThreshold OBJECT-TYPE
			SYNTAX OCTET STRING (SIZE (1..32))
			MAX-ACCESS read-write
			STATUS current
			DESCRIPTION
				"Fiber length change threshold, unit m, Default value:100m."
			::= { pstIFMS1000MeasureEntry 13 } 			

			
		-- 1.3.6.1.4.1.48391.3.5.2.1.14
		pstIFMS1000MeasureEndToEndLossHighThreshold OBJECT-TYPE
			SYNTAX OCTET STRING (SIZE (1..32))
			MAX-ACCESS read-write
			STATUS current
			DESCRIPTION
				"End to end loss change, unit dB, Critical alarm, Default value:5dB."
			::= { pstIFMS1000MeasureEntry 14 }			

			
		-- 1.3.6.1.4.1.48391.3.5.2.1.15
		pstIFMS1000MeasureEndToEndLossMiddleThreshold OBJECT-TYPE
			SYNTAX OCTET STRING (SIZE (1..32))
			MAX-ACCESS read-write
			STATUS current
			DESCRIPTION
				"End to end loss change, unit dB, Major alarm, Default value:1dB."
			::= { pstIFMS1000MeasureEntry 15 }				

			
		-- 1.3.6.1.4.1.48391.3.5.2.1.16
		pstIFMS1000MeasureEndToEndLossLowThreshold OBJECT-TYPE
			SYNTAX OCTET STRING (SIZE (1..32))
			MAX-ACCESS read-write
			STATUS current
			DESCRIPTION
				"End to end loss change, unit dB, Minor alarm, Default value:0dB."
			::= { pstIFMS1000MeasureEntry 16 }			

			
		-- 1.3.6.1.4.1.48391.3.5.2.1.17
		pstIFMS1000MeasureNewLossCriticalThreshold OBJECT-TYPE
			SYNTAX OCTET STRING (SIZE (1..32))
			MAX-ACCESS read-write
			STATUS current
			DESCRIPTION
				"Loss changes of new events, unit dB, Critical alarm, Default value:5dB."
			::= { pstIFMS1000MeasureEntry 17 }			

						
		-- 1.3.6.1.4.1.48391.3.5.2.1.18
		pstIFMS1000MeasureNewLossMajorThreshold OBJECT-TYPE
			SYNTAX OCTET STRING (SIZE (1..32))
			MAX-ACCESS read-write
			STATUS current
			DESCRIPTION
				"Loss changes of new events, unit dB, Major alarm, Default value:2dB."
			::= { pstIFMS1000MeasureEntry 18 }	

			
		-- 1.3.6.1.4.1.48391.3.5.2.1.19
		pstIFMS1000MeasureNewLossMinorThreshold OBJECT-TYPE
			SYNTAX OCTET STRING (SIZE (1..32))
			MAX-ACCESS read-write
			STATUS current
			DESCRIPTION
				"Loss changes of new events, unit dB, Minor alarm, Default value:0.5dB."
			::= { pstIFMS1000MeasureEntry 19 }		

			
		-- 1.3.6.1.4.1.48391.3.5.2.1.20
		pstIFMS1000MeasureOldLossCriticalThreshold OBJECT-TYPE
			SYNTAX OCTET STRING (SIZE (1..32))
			MAX-ACCESS read-write
			STATUS current
			DESCRIPTION
				"Changes in loss of events, unit dB, Critical alarm, Default value:5dB."
			::= { pstIFMS1000MeasureEntry 20 }			

						
		-- 1.3.6.1.4.1.48391.3.5.2.1.21
		pstIFMS1000MeasureOldLossMajorThreshold OBJECT-TYPE
			SYNTAX OCTET STRING (SIZE (1..32))
			MAX-ACCESS read-write
			STATUS current
			DESCRIPTION
				"Changes in loss of events, unit dB, Major alarm, Default value:2dB."
			::= { pstIFMS1000MeasureEntry 21 }				   			


 		-- 1.3.6.1.4.1.48391.3.5.2.1.22
		pstIFMS1000MeasureOldLossMinorThreshold OBJECT-TYPE
			SYNTAX OCTET STRING (SIZE (1..32))
			MAX-ACCESS read-write
			STATUS current
			DESCRIPTION
				"Changes in loss of events, unit dB, Minor alarm, Default value:0.5dB."
			::= { pstIFMS1000MeasureEntry 22 }	


 		-- 1.3.6.1.4.1.48391.3.5.2.1.23
		pstIFMS1000MeasureEventPositionChangeThreshold OBJECT-TYPE   
			SYNTAX OCTET STRING (SIZE (1..32))       
			UNITS "m"
			MAX-ACCESS read-write
			STATUS current
			DESCRIPTION
				"Event Position change threshold, unit m, Default value:100m."
			::= { pstIFMS1000MeasureEntry 23 } 
			
	
 		-- 1.3.6.1.4.1.48391.3.5.2.1.24
		pstIFMS1000MeasureReserved2 OBJECT-TYPE
			SYNTAX OCTET STRING (SIZE (1..32))
			MAX-ACCESS read-write
			STATUS current
			DESCRIPTION
				""
			::= { pstIFMS1000MeasureEntry 24 }	    
			

 		-- 1.3.6.1.4.1.48391.3.5.2.1.25
		pstIFMS1000MeasureNumber OBJECT-TYPE
			SYNTAX OCTET STRING (SIZE (1..32))
			MAX-ACCESS read-only
			STATUS current
			DESCRIPTION
				"The number of scanned times that have been completed in automatic monitoring."
			::= { pstIFMS1000MeasureEntry 25 }	
                                             
                                             
 		-- 1.3.6.1.4.1.48391.3.5.2.1.26
		pstIFMS1000MeasureNumberSORStoredEachChannel OBJECT-TYPE
			SYNTAX OCTET STRING (SIZE (1..32))
			MAX-ACCESS read-write
			STATUS current
			DESCRIPTION
				"The maximum number of SOR files per channel can be stored in FLAH automatically."
			::= { pstIFMS1000MeasureEntry 26 }	


			
					
		-- 1.3.6.1.4.1.48391.3.5.3
		pstIFMS1000FingerTable OBJECT-TYPE
			SYNTAX SEQUENCE OF PSTIFMS1000FingerEntry
			MAX-ACCESS not-accessible
			STATUS current
			DESCRIPTION
				"Description."
			::= { pstIFMS1000 3 }

		
		-- 1.3.6.1.4.1.48391.3.5.3.1
		pstIFMS1000FingerEntry OBJECT-TYPE
			SYNTAX PSTIFMS1000FingerEntry
			MAX-ACCESS not-accessible
			STATUS current
			DESCRIPTION
				"Description."
			INDEX { pstIFMS1000FTPortNum }
			::= { pstIFMS1000FingerTable 1 }

		
		PSTIFMS1000FingerEntry ::=
			SEQUENCE { 
				pstIFMS1000FTPortNum
					Integer32,
				pstIFMS1000FingerStartPosition
					OCTET STRING,
				pstIFMS1000FingerEndPosition
					OCTET STRING,
				pstIFMS1000FingerRefIndex
					OCTET STRING,
				pstIFMS1000FingerResolution
					OCTET STRING,
				pstIFMS1000FingerCreateTime
					OCTET STRING,
				pstIFMS1000FingerFileStatus
					Integer32,
				pstIFMS1000FingerAction
					Integer32,
				pstIFMS1000FingerActionStatus
					Integer32,
				pstIFMS1000FingerSavedFileName
					OCTET STRING,
				pstIFMS1000FingerCurrentFileName
					OCTET STRING
			 }

		-- 1.3.6.1.4.1.48391.3.5.3.1.1
		pstIFMS1000FTPortNum OBJECT-TYPE
			SYNTAX Integer32 (1..8)
			MAX-ACCESS read-only
			STATUS current
			DESCRIPTION
				"Description."
			::= { pstIFMS1000FingerEntry 1 }     
			
			
		-- 1.3.6.1.4.1.48391.3.5.3.1.2
		pstIFMS1000FingerStartPosition OBJECT-TYPE
			SYNTAX OCTET STRING (SIZE (1..32))
			UNITS "Meter"
			MAX-ACCESS read-write
			STATUS current
			DESCRIPTION
				"The Start position in the finger measurement. "
			::= { pstIFMS1000FingerEntry 2 }

			
		-- 1.3.6.1.4.1.48391.3.5.3.1.3
		pstIFMS1000FingerEndPosition OBJECT-TYPE
			SYNTAX OCTET STRING (SIZE (1..32))
			UNITS "Meter"
			MAX-ACCESS read-write
			STATUS current
			DESCRIPTION
				"The end position in the finger measurement. "
			::= { pstIFMS1000FingerEntry 3 }

		
		-- 1.3.6.1.4.1.48391.3.5.3.1.4
		pstIFMS1000FingerRefIndex OBJECT-TYPE
			SYNTAX OCTET STRING (SIZE (1..32))
			MAX-ACCESS read-write
			STATUS current
			DESCRIPTION
				"The refractive index in the finger measurement."
			::= { pstIFMS1000FingerEntry 4 }

		
-- The resolution must be the power of 2. For example, 1,2,4,8,16...
		-- 1.3.6.1.4.1.48391.3.5.3.1.5
		pstIFMS1000FingerResolution OBJECT-TYPE
			SYNTAX OCTET STRING (SIZE (1..32))
			UNITS "Meter"
			MAX-ACCESS read-write
			STATUS current
			DESCRIPTION
				"The resolution in the finger measurement."
			::= { pstIFMS1000FingerEntry 5 }

		
		-- 1.3.6.1.4.1.48391.3.5.3.1.6
		pstIFMS1000FingerCreateTime OBJECT-TYPE
			SYNTAX OCTET STRING (SIZE (1..64))
			MAX-ACCESS read-only
			STATUS current
			DESCRIPTION
				"The time when the finger is generated."
			::= { pstIFMS1000FingerEntry 6 }

		
		-- 1.3.6.1.4.1.48391.3.5.3.1.7
		pstIFMS1000FingerFileStatus OBJECT-TYPE
			SYNTAX Integer32 (0..2)
			MAX-ACCESS read-only
			STATUS current
			DESCRIPTION
				"Indicates whether the fingerprint file is saved or obsolete.
				0. No
				1. Yes
				2. Obsolete."
			::= { pstIFMS1000FingerEntry 7 }

		
		-- 1.3.6.1.4.1.48391.3.5.3.1.8
		pstIFMS1000FingerAction OBJECT-TYPE
			SYNTAX Integer32 (1..4)
			UNITS "Meter"
			MAX-ACCESS read-write
			STATUS current
			DESCRIPTION
				"1. Start measurement for finger print
				2. Save current fingerprint file
				3. Delete currennt fingerprint file.
				4. Stop action."
			::= { pstIFMS1000FingerEntry 8 }

		
		-- 1.3.6.1.4.1.48391.3.5.3.1.9
		pstIFMS1000FingerActionStatus OBJECT-TYPE
			SYNTAX Integer32 (0..3)
			MAX-ACCESS read-only
			STATUS current
			DESCRIPTION
				"Indicates the status of fingerprint action.
				0. Idle 
				1. Running
				2. Done
				3. Failed."
			::= { pstIFMS1000FingerEntry 9 }

		
		-- 1.3.6.1.4.1.48391.3.5.3.1.10
		pstIFMS1000FingerSavedFileName OBJECT-TYPE
			SYNTAX OCTET STRING (SIZE (1..128))
			MAX-ACCESS read-only
			STATUS current
			DESCRIPTION
				"The file name which will be saved in the file. You can get the result file by FTP. 
				This field is only valid after a measurement is finished in a single measurement or a diff is found in auto measurement."
			::= { pstIFMS1000FingerEntry 10 }

		
		-- 1.3.6.1.4.1.48391.3.5.3.1.11
		pstIFMS1000FingerCurrentFileName OBJECT-TYPE
			SYNTAX OCTET STRING (SIZE (1..128))
			MAX-ACCESS read-only
			STATUS current
			DESCRIPTION
				"The file name which will be saved in the file. You can get the result file by FTP. 
				This field is only valid after a measurement is finished in a single measurement or a diff is found in auto measurement."
			::= { pstIFMS1000FingerEntry 11 }

		
		-- 1.3.6.1.4.1.48391.3.5.4
		pstIFMS1000DiffInfo OBJECT-IDENTITY
			STATUS current
			DESCRIPTION 
				"Description."
			::= { pstIFMS1000 4 }

		
		-- 1.3.6.1.4.1.48391.3.5.4.1
		pstIFMS1000DiffTotalTable OBJECT-TYPE
			SYNTAX SEQUENCE OF PSTIFMS1000DiffTotalEntry
			MAX-ACCESS not-accessible
			STATUS current
			DESCRIPTION
				"Description."
			::= { pstIFMS1000DiffInfo 1 }

		
		-- 1.3.6.1.4.1.48391.3.5.4.1.1
		pstIFMS1000DiffTotalEntry OBJECT-TYPE
			SYNTAX PSTIFMS1000DiffTotalEntry
			MAX-ACCESS not-accessible
			STATUS current
			DESCRIPTION
				"Description."
			INDEX { pstIFMS1000DtPortNum }
			::= { pstIFMS1000DiffTotalTable 1 }

		
		PSTIFMS1000DiffTotalEntry ::=
			SEQUENCE { 
				pstIFMS1000DtPortNum
					Integer32,
				pstIFMS1000DtTotalNum
					Integer32,
				pstIFMS1000DtDiffDetail
					OCTET STRING,  
				pstIFMS1000DtDiffDetailStatus
					Integer32
			 }

		-- 1.3.6.1.4.1.48391.3.5.4.1.1.1
		pstIFMS1000DtPortNum OBJECT-TYPE
			SYNTAX Integer32
			MAX-ACCESS read-only
			STATUS current
			DESCRIPTION
				"Description."
			::= { pstIFMS1000DiffTotalEntry 1 }

		
		-- 1.3.6.1.4.1.48391.3.5.4.1.1.2
		pstIFMS1000DtTotalNum OBJECT-TYPE
			SYNTAX Integer32
			MAX-ACCESS read-only
			STATUS current
			DESCRIPTION
				"Indicates the diff table's total index count of one port"      
			::= { pstIFMS1000DiffTotalEntry 2 }       
			
			
		-- 1.3.6.1.4.1.48391.3.5.4.1.1.3
		pstIFMS1000DtDiffDetail OBJECT-TYPE
			SYNTAX OCTET STRING (SIZE (1..512))
			MAX-ACCESS read-only
			STATUS current
			DESCRIPTION
				"Indicates the fiber's diff detail of the port.
					e.g. :  CH1,A,3,5,50.28,40.13,CH1,A,10,5,0.21,5.6				
				"    
			::= { pstIFMS1000DiffTotalEntry 3 } 
			

		-- 1.3.6.1.4.1.48391.3.5.4.1.1.4
		pstIFMS1000DtDiffDetailStatus OBJECT-TYPE
			SYNTAX Integer32
			MAX-ACCESS read-only
			STATUS current
			DESCRIPTION
				"Indicates the DiffDetail status: 
				0:not ready, can not be read
				1:ready, can be read"      
			::= { pstIFMS1000DiffTotalEntry 4 }  
			
					
		-- 1.3.6.1.4.1.48391.3.5.4.2
		pstIFMS1000DiffInfoTable OBJECT-TYPE
			SYNTAX SEQUENCE OF PSTIFMS1000DiffInfoEntry
			MAX-ACCESS not-accessible
			STATUS current
			DESCRIPTION
				"Description."
			::= { pstIFMS1000DiffInfo 2 }

		
		-- 1.3.6.1.4.1.48391.3.5.4.2.1
		pstIFMS1000DiffInfoEntry OBJECT-TYPE
			SYNTAX PSTIFMS1000DiffInfoEntry
			MAX-ACCESS not-accessible
			STATUS current
			DESCRIPTION
				"Description."
			INDEX { pstIFMS1000DiffInfoPortNum, pstIFMS1000DiffInfoPortItemIndex }
			::= { pstIFMS1000DiffInfoTable 1 }

		
		PSTIFMS1000DiffInfoEntry ::=
			SEQUENCE { 
				pstIFMS1000DiffInfoPortNum
					Integer32,
				pstIFMS1000DiffInfoPortItemIndex
					Integer32,
				pstIFMS1000DiffInfoDistance
					OCTET STRING,
				pstIFMS1000DiffInfoNVal
					OCTET STRING,
				pstIFMS1000DiffInfodBVal
					OCTET STRING,
				pstIFMS1000DiffInfoDiffType
					Integer32,
				pstIFMS1000DiffInfoPointId
					Unsigned32
			 }

		-- 1.3.6.1.4.1.48391.3.5.4.2.1.1
		pstIFMS1000DiffInfoPortNum OBJECT-TYPE
			SYNTAX Integer32
			MAX-ACCESS read-only
			STATUS current
			DESCRIPTION
				"Description."
			::= { pstIFMS1000DiffInfoEntry 1 }

		
		-- 1.3.6.1.4.1.48391.3.5.4.2.1.2
		pstIFMS1000DiffInfoPortItemIndex OBJECT-TYPE
			SYNTAX Integer32
			MAX-ACCESS read-only
			STATUS current
			DESCRIPTION
				"Description."
			::= { pstIFMS1000DiffInfoEntry 2 }

		
		-- 1.3.6.1.4.1.48391.3.5.4.2.1.3
		pstIFMS1000DiffInfoDistance OBJECT-TYPE
			SYNTAX OCTET STRING (SIZE (1..32))
			MAX-ACCESS read-only
			STATUS current
			DESCRIPTION
				"Description."
			::= { pstIFMS1000DiffInfoEntry 3 }

		
		-- 1.3.6.1.4.1.48391.3.5.4.2.1.4
		pstIFMS1000DiffInfoNVal OBJECT-TYPE
			SYNTAX OCTET STRING (SIZE (1..32))
			MAX-ACCESS read-only
			STATUS current
			DESCRIPTION
				"Description."
			::= { pstIFMS1000DiffInfoEntry 4 }

		
		-- 1.3.6.1.4.1.48391.3.5.4.2.1.5
		pstIFMS1000DiffInfodBVal OBJECT-TYPE
			SYNTAX OCTET STRING (SIZE (1..32))
			MAX-ACCESS read-only
			STATUS current
			DESCRIPTION
				"Description."
			::= { pstIFMS1000DiffInfoEntry 5 }

		
		-- 1.3.6.1.4.1.48391.3.5.4.2.1.6
		pstIFMS1000DiffInfoDiffType OBJECT-TYPE
			SYNTAX Integer32
			MAX-ACCESS read-only
			STATUS current
			DESCRIPTION
				"Point's event.
				1. New point is found.
				2. Point missed.
				3. Point's condition is changed but still in the range.
				4. Point is resumed.
				5. Point found uncertain.
				6. Point missed uncertain.
				7. Point found in minor.
				8. Point found in major.
				9. Point changed in minor.
				10.Point changed in major."
			::= { pstIFMS1000DiffInfoEntry 6 }

		
		-- 1.3.6.1.4.1.48391.3.5.4.2.1.7
		pstIFMS1000DiffInfoPointId OBJECT-TYPE
			SYNTAX Unsigned32
			MAX-ACCESS read-only
			STATUS current
			DESCRIPTION
				"Point's ID. Each point has a specific ID."
			::= { pstIFMS1000DiffInfoEntry 7 }

		
		-- 1.3.6.1.4.1.48391.3.5.5
		pstIFMS1000Notifications OBJECT-IDENTITY
			STATUS current
			DESCRIPTION 
				"Description."
			::= { pstIFMS1000 5 }

		
		-- 1.3.6.1.4.1.48391.3.5.5.1
		pstIFMS1000MeasureEvent NOTIFICATION-TYPE
			OBJECTS { pstIFMS1000MeasureStatus }
			STATUS current
			DESCRIPTION 
				"The measurement status is changed."
			::= { pstIFMS1000Notifications 1 }

		
		-- 1.3.6.1.4.1.48391.3.5.6
		pstIFMS1000LedStatus OBJECT-IDENTITY
			STATUS current
			DESCRIPTION 
				"Description."
			::= { pstIFMS1000 6 }

		
		-- 1.3.6.1.4.1.48391.3.5.6.1
		pstIFMS1000SystemLed OBJECT-IDENTITY
			STATUS current
			DESCRIPTION 
				"Description."
			::= { pstIFMS1000LedStatus 1 }

	
		-- 1.3.6.1.4.1.48391.3.5.6.1.1
		pstIFMS1000SysLedFan1 OBJECT-TYPE
			SYNTAX Integer32
			MAX-ACCESS read-only
			STATUS current
			DESCRIPTION
				"The operating state of the fan1:0,fault(RED);1,OK(GREEN)."
			::= { pstIFMS1000SystemLed 1 }

		
		-- 1.3.6.1.4.1.48391.3.5.6.1.2
		pstIFMS1000SysLedFan2 OBJECT-TYPE
			SYNTAX Integer32
			MAX-ACCESS read-only
			STATUS current
			DESCRIPTION
				"The operating state of the fan2:0,fault(RED);1,OK(GREEN)."
			::= { pstIFMS1000SystemLed 2 }

		
		-- 1.3.6.1.4.1.48391.3.5.6.1.3
		pstIFMS1000SysLedStatus OBJECT-TYPE
			SYNTAX Integer32
			MAX-ACCESS read-only
			STATUS current
			DESCRIPTION
				"The operating state of the System:0,fault(RED);1,OK(GREEN)."
			::= { pstIFMS1000SystemLed 3 }

		
		-- 1.3.6.1.4.1.48391.3.5.6.2
		pstIFMS1000PortLedTable OBJECT-TYPE
			SYNTAX SEQUENCE OF PSTIFMS1000PortLedEntry
			MAX-ACCESS not-accessible
			STATUS current
			DESCRIPTION
				"Description."
			::= { pstIFMS1000LedStatus 2 }

		
		-- 1.3.6.1.4.1.48391.3.5.6.2.1
		pstIFMS1000PortLedEntry OBJECT-TYPE
			SYNTAX PSTIFMS1000PortLedEntry
			MAX-ACCESS not-accessible
			STATUS current
			DESCRIPTION
				"Description."
			INDEX { pstIFMS1000PortLedPortNum }
			::= { pstIFMS1000PortLedTable 1 }

		
		PSTIFMS1000PortLedEntry ::=
			SEQUENCE { 
				pstIFMS1000PortLedPortNum
					Integer32,
				pstIFMS1000PortLedStatus
					Integer32
			 }

		-- 1.3.6.1.4.1.48391.3.5.6.2.1.1
		pstIFMS1000PortLedPortNum OBJECT-TYPE
			SYNTAX Integer32
			MAX-ACCESS read-only
			STATUS current
			DESCRIPTION
				"Description."
			::= { pstIFMS1000PortLedEntry 1 }

		
		-- 1.3.6.1.4.1.48391.3.5.6.2.1.2
		pstIFMS1000PortLedStatus OBJECT-TYPE
			SYNTAX Integer32
			MAX-ACCESS read-write
			STATUS current
			DESCRIPTION
				"The operating state of the CHn:0,fault(RED);1,OK(GREEN)."
			::= { pstIFMS1000PortLedEntry 2 }

		
		-- 1.3.6.1.4.1.48391.3.5.7
		pstIFMS1000DiagnoseTable OBJECT-TYPE
			SYNTAX SEQUENCE OF PSTIFMS1000DiagnoseEntry
			MAX-ACCESS not-accessible
			STATUS current
			DESCRIPTION
				"Description."
			::= { pstIFMS1000 7 }

		
		-- 1.3.6.1.4.1.48391.3.5.7.1
		pstIFMS1000DiagnoseEntry OBJECT-TYPE
			SYNTAX PSTIFMS1000DiagnoseEntry
			MAX-ACCESS not-accessible
			STATUS current
			DESCRIPTION
				"Description."
			INDEX { pstIFMS1000DgPortNum }
			::= { pstIFMS1000DiagnoseTable 1 }

		
		PSTIFMS1000DiagnoseEntry ::=
			SEQUENCE { 
				pstIFMS1000DgPortNum
					Integer32,
				pstIFMS1000DgLaserACBias
					OCTET STRING,
				pstIFMS1000DgLaserDCBias
					OCTET STRING,
				pstIFMS1000DgLaserACModulation
					OCTET STRING,
				pstIFMS1000DgLaserDCModulation
					OCTET STRING,
				pstIFMS1000DgLaserEn
					Integer32,
				pstIFMS1000DgPwm
					Integer32,
				pstIFMS1000DgSeed
					Integer32,
				pstIFMS1000DgPrbs
					Integer32,
				pstIFMS1000DgAverage
					Integer32,
				pstIFMS1000DgRegAddr
					Integer32,
				pstIFMS1000DgRegValue
					Integer32,
				pstIFMS1000DgMaskStartPoint
					OCTET STRING,
				pstIFMS1000DgMaskStopPoint
					OCTET STRING,
				pstIFMS1000DgMaskAction
					Integer32,
				pstIFMS1000DgMeasureDeltaThld
					OCTET STRING,
				pstIFMS1000DgCutPointThld
					OCTET STRING,
				pstIFMS1000DgPeriod
					Integer32,
				pstIFMS1000DgDAC
					Integer32,
				pstIFMS1000DgCounterClockMode
					Integer32,
				pstIFMS1000DgScanRunType
					Integer32,
				pstIFMS1000DgOpt
					Unsigned32,
				pstIFMS1000DgFiberOffset
					OCTET STRING,
				pstIFMS1000DgTestWaveLen
					Unsigned32,
				pstIFMS1000DgPRT
					Unsigned32,
				pstIFMS1000DgPPW
					Unsigned32,
				pstIFMS1000DgPPrescale
					Unsigned32,
				pstIFMS1000DgPAvg
					Unsigned32,
				pstIFMS1000DgPGain
					Unsigned32,
				pstIFMS1000DgPAdcData
					Unsigned32,
				pstIFMS1000DgPE2promAction
					Unsigned32
			 }

		-- 1.3.6.1.4.1.48391.3.5.7.1.1
		pstIFMS1000DgPortNum OBJECT-TYPE
			SYNTAX Integer32 (1..8)
			MAX-ACCESS read-only
			STATUS current
			DESCRIPTION
				"Description."
			::= { pstIFMS1000DiagnoseEntry 1 }

		
		-- 1.3.6.1.4.1.48391.3.5.7.1.2
		pstIFMS1000DgLaserACBias OBJECT-TYPE
			SYNTAX OCTET STRING (SIZE (1..8))
			MAX-ACCESS read-write
			STATUS current
			DESCRIPTION
				"Description."
			::= { pstIFMS1000DiagnoseEntry 2 }

		
		-- 1.3.6.1.4.1.48391.3.5.7.1.3
		pstIFMS1000DgLaserDCBias OBJECT-TYPE
			SYNTAX OCTET STRING (SIZE (1..8))
			MAX-ACCESS read-write
			STATUS current
			DESCRIPTION
				"Description."
			::= { pstIFMS1000DiagnoseEntry 3 }

		
		-- 1.3.6.1.4.1.48391.3.5.7.1.4
		pstIFMS1000DgLaserACModulation OBJECT-TYPE
			SYNTAX OCTET STRING (SIZE (1..8))
			MAX-ACCESS read-write
			STATUS current
			DESCRIPTION
				"Description."
			::= { pstIFMS1000DiagnoseEntry 4 }

		
		-- 1.3.6.1.4.1.48391.3.5.7.1.5
		pstIFMS1000DgLaserDCModulation OBJECT-TYPE
			SYNTAX OCTET STRING (SIZE (1..8))
			MAX-ACCESS read-write
			STATUS current
			DESCRIPTION
				"Description."
			::= { pstIFMS1000DiagnoseEntry 5 }

		
		-- 1.3.6.1.4.1.48391.3.5.7.1.6
		pstIFMS1000DgLaserEn OBJECT-TYPE
			SYNTAX Integer32 (0..1)
			MAX-ACCESS read-write
			STATUS current
			DESCRIPTION
				"Laser Switch.
				0. Disable laser.
				1. Enable laser."
			::= { pstIFMS1000DiagnoseEntry 6 }

		
		-- 1.3.6.1.4.1.48391.3.5.7.1.7
		pstIFMS1000DgPwm OBJECT-TYPE
			SYNTAX Integer32
			MAX-ACCESS read-write
			STATUS current
			DESCRIPTION
				"Description."
			::= { pstIFMS1000DiagnoseEntry 7 }

		
		-- 1.3.6.1.4.1.48391.3.5.7.1.8
		pstIFMS1000DgSeed OBJECT-TYPE
			SYNTAX Integer32
			MAX-ACCESS read-write
			STATUS current
			DESCRIPTION
				"Description."
			::= { pstIFMS1000DiagnoseEntry 8 }

		
-- 0. PRBS7
-- 1. PRBS11
-- 2. PRBS31
		-- 1.3.6.1.4.1.48391.3.5.7.1.9
		pstIFMS1000DgPrbs OBJECT-TYPE
			SYNTAX Integer32
			MAX-ACCESS read-write
			STATUS current
			DESCRIPTION
				"Description."
			::= { pstIFMS1000DiagnoseEntry 9 }

		
		-- 1.3.6.1.4.1.48391.3.5.7.1.10
		pstIFMS1000DgAverage OBJECT-TYPE
			SYNTAX Integer32
			MAX-ACCESS read-write
			STATUS current
			DESCRIPTION
				"Description."
			::= { pstIFMS1000DiagnoseEntry 10 }

		
		-- 1.3.6.1.4.1.48391.3.5.7.1.11
		pstIFMS1000DgRegAddr OBJECT-TYPE
			SYNTAX Integer32
			MAX-ACCESS read-write
			STATUS current
			DESCRIPTION
				"The action of reading reg value is obsoleted now."
			::= { pstIFMS1000DiagnoseEntry 11 }

		
		-- 1.3.6.1.4.1.48391.3.5.7.1.12
		pstIFMS1000DgRegValue OBJECT-TYPE
			SYNTAX Integer32
			MAX-ACCESS read-write
			STATUS current
			DESCRIPTION
				"The action of reading reg value is obsoleted now."
			::= { pstIFMS1000DiagnoseEntry 12 }

		
		-- 1.3.6.1.4.1.48391.3.5.7.1.13
		pstIFMS1000DgMaskStartPoint OBJECT-TYPE
			SYNTAX OCTET STRING (SIZE (1..32))
			MAX-ACCESS read-write
			STATUS current
			DESCRIPTION
				"The start point of the mask setting this time."
			::= { pstIFMS1000DiagnoseEntry 13 }

		
		-- 1.3.6.1.4.1.48391.3.5.7.1.14
		pstIFMS1000DgMaskStopPoint OBJECT-TYPE
			SYNTAX OCTET STRING (SIZE (1..32))
			MAX-ACCESS read-write
			STATUS current
			DESCRIPTION
				"The start point of the mask setting this time."
			::= { pstIFMS1000DiagnoseEntry 14 }

		
		-- 1.3.6.1.4.1.48391.3.5.7.1.15
		pstIFMS1000DgMaskAction OBJECT-TYPE
			SYNTAX Integer32 (1..5)
			MAX-ACCESS read-write
			STATUS current
			DESCRIPTION
				"1. Mask a range from 'pstIFMS1000DgMaskStartPoint' to 'pstIFMS1000DgMaskStopPoint'
				2. Unmask a range from 'pstIFMS1000DgMaskStartPoint' to 'pstIFMS1000DgMaskStopPoint'
				3. Mask all
				4. Unmask all
				5. Get mask result. The result will be got from a file."
			::= { pstIFMS1000DiagnoseEntry 15 }

		
		-- 1.3.6.1.4.1.48391.3.5.7.1.16
		pstIFMS1000DgMeasureDeltaThld OBJECT-TYPE
			SYNTAX OCTET STRING (SIZE (1..32))
			MAX-ACCESS read-write
			STATUS current
			DESCRIPTION
				"The delta threshold in measurement. It should be a float value."
			::= { pstIFMS1000DiagnoseEntry 16 }

		
		-- 1.3.6.1.4.1.48391.3.5.7.1.17
		pstIFMS1000DgCutPointThld OBJECT-TYPE
			SYNTAX OCTET STRING (SIZE (1..32))
			MAX-ACCESS read-write
			STATUS current
			DESCRIPTION
				"Description."
			::= { pstIFMS1000DiagnoseEntry 17 }

		
		-- 1.3.6.1.4.1.48391.3.5.7.1.18
		pstIFMS1000DgPeriod OBJECT-TYPE
			SYNTAX Integer32
			MAX-ACCESS read-write
			STATUS current
			DESCRIPTION			" "
			::= { pstIFMS1000DiagnoseEntry 18 }

		
		-- 1.3.6.1.4.1.48391.3.5.7.1.19
		pstIFMS1000DgDAC OBJECT-TYPE
			SYNTAX Integer32
			MAX-ACCESS read-write
			STATUS current
			DESCRIPTION			" "
			::= { pstIFMS1000DiagnoseEntry 19 }

		
		-- 1.3.6.1.4.1.48391.3.5.7.1.20
		pstIFMS1000DgCounterClockMode OBJECT-TYPE
			SYNTAX Integer32 (0..1)
			MAX-ACCESS read-write
			STATUS current
			DESCRIPTION
				"0.Normal
				1.Invert"
			::= { pstIFMS1000DiagnoseEntry 20 }

		
		-- 1.3.6.1.4.1.48391.3.5.7.1.21
		pstIFMS1000DgScanRunType OBJECT-TYPE
			SYNTAX Integer32 (1..2)
			MAX-ACCESS read-write
			STATUS current
			DESCRIPTION
				"1. Full scan
				2. Fast scan"
			::= { pstIFMS1000DiagnoseEntry 21 }

		
		-- 1.3.6.1.4.1.48391.3.5.7.1.22
		pstIFMS1000DgOpt OBJECT-TYPE
			SYNTAX Unsigned32
			MAX-ACCESS read-write
			STATUS current
			DESCRIPTION
				"1. Full scan
				2. Fast scan"
			::= { pstIFMS1000DiagnoseEntry 22 }

		
		-- 1.3.6.1.4.1.48391.3.5.7.1.23
		pstIFMS1000DgFiberOffset OBJECT-TYPE
			SYNTAX OCTET STRING (SIZE (1..32))
			UNITS "Meter"
			MAX-ACCESS read-write
			STATUS current
			DESCRIPTION
				"The fiber's offset which used to skip the internal fiber offset."
			::= { pstIFMS1000DiagnoseEntry 23 }

		
		-- 1.3.6.1.4.1.48391.3.5.7.1.24
		pstIFMS1000DgTestWaveLen OBJECT-TYPE
			SYNTAX Unsigned32
			UNITS "nm"
			MAX-ACCESS read-write
			STATUS current
			DESCRIPTION
				"The wavelength of monitor signal."
			::= { pstIFMS1000DiagnoseEntry 24 }

		
		-- 1.3.6.1.4.1.48391.3.5.7.1.25
		pstIFMS1000DgPRT OBJECT-TYPE
			SYNTAX Unsigned32
			MAX-ACCESS read-write
			STATUS current
			DESCRIPTION
				"The repeat time(test period) in POTDR."
			::= { pstIFMS1000DiagnoseEntry 25 }

		
		-- 1.3.6.1.4.1.48391.3.5.7.1.26
		pstIFMS1000DgPPW OBJECT-TYPE
			SYNTAX Unsigned32
			MAX-ACCESS read-write
			STATUS current
			DESCRIPTION
				"The pulse width in POTDR."
			::= { pstIFMS1000DiagnoseEntry 26 }

		
		-- 1.3.6.1.4.1.48391.3.5.7.1.27
		pstIFMS1000DgPPrescale OBJECT-TYPE
			SYNTAX Unsigned32
			MAX-ACCESS read-write
			STATUS current
			DESCRIPTION
				"The prescale in POTDR."
			::= { pstIFMS1000DiagnoseEntry 27 }

		
		-- 1.3.6.1.4.1.48391.3.5.7.1.28
		pstIFMS1000DgPAvg OBJECT-TYPE
			SYNTAX Unsigned32
			MAX-ACCESS read-write
			STATUS current
			DESCRIPTION
				"The value of POTDR accumulate."
			::= { pstIFMS1000DiagnoseEntry 28 }

		
		-- 1.3.6.1.4.1.48391.3.5.7.1.29
		pstIFMS1000DgPGain OBJECT-TYPE
			SYNTAX Unsigned32
			MAX-ACCESS read-write
			STATUS current
			DESCRIPTION
				"The value of POTDR Gain."
			::= { pstIFMS1000DiagnoseEntry 29 }

		
		-- 1.3.6.1.4.1.48391.3.5.7.1.30
		pstIFMS1000DgPAdcData OBJECT-TYPE
			SYNTAX Unsigned32
			MAX-ACCESS read-only
			STATUS current
			DESCRIPTION
				"The value of POTDR ADC."
			::= { pstIFMS1000DiagnoseEntry 30 }

		
		-- 1.3.6.1.4.1.48391.3.5.7.1.31
		pstIFMS1000DgPE2promAction OBJECT-TYPE
			SYNTAX Unsigned32 (1..2)
			UNITS "Meter"
			MAX-ACCESS read-write
			STATUS current
			DESCRIPTION
				"The action to EEPROM.
				1. Save.
				2. Reset to factory settings."
			::= { pstIFMS1000DiagnoseEntry 31 }

		
		-- 1.3.6.1.4.1.48391.3.5.8
		pstIFMS1000DebugRegTable OBJECT-TYPE
			SYNTAX SEQUENCE OF PSTIFMS1000DebugRegEntry
			MAX-ACCESS not-accessible
			STATUS current
			DESCRIPTION
				"Description."
			::= { pstIFMS1000 8 }

		
		-- 1.3.6.1.4.1.48391.3.5.8.1
		pstIFMS1000DebugRegEntry OBJECT-TYPE
			SYNTAX PSTIFMS1000DebugRegEntry
			MAX-ACCESS not-accessible
			STATUS current
			DESCRIPTION
				"Description."
			INDEX { pstIFMS1000DbPortNum }
			::= { pstIFMS1000DebugRegTable 1 }

		
		PSTIFMS1000DebugRegEntry ::=
			SEQUENCE { 
				pstIFMS1000DbPortNum
					Integer32,
				pstIFMS1000DbRegAddr
					Integer32,
				pstIFMS1000DbRegValue
					Integer32
			 }

		-- 1.3.6.1.4.1.48391.3.5.8.1.1
		pstIFMS1000DbPortNum OBJECT-TYPE
			SYNTAX Integer32 (1..8)
			MAX-ACCESS read-only
			STATUS current
			DESCRIPTION
				"Description."
			::= { pstIFMS1000DebugRegEntry 1 }

		
		-- 1.3.6.1.4.1.48391.3.5.8.1.11
		pstIFMS1000DbRegAddr OBJECT-TYPE
			SYNTAX Integer32
			MAX-ACCESS read-write
			STATUS current
			DESCRIPTION			" "
			::= { pstIFMS1000DebugRegEntry 11 }

		
		-- 1.3.6.1.4.1.48391.3.5.8.1.12
		pstIFMS1000DbRegValue OBJECT-TYPE
			SYNTAX Integer32
			MAX-ACCESS read-write
			STATUS current
			DESCRIPTION			" "
			::= { pstIFMS1000DebugRegEntry 12 }

		
		-- 1.3.6.1.4.1.48391.3.5.9
		pstIFMS1000DebugDACTable OBJECT-TYPE
			SYNTAX SEQUENCE OF PSTIFMS1000DebugDACEntry
			MAX-ACCESS not-accessible
			STATUS current
			DESCRIPTION
				"Description."
			::= { pstIFMS1000 9 }

		
		-- 1.3.6.1.4.1.48391.3.5.9.1
		pstIFMS1000DebugDACEntry OBJECT-TYPE
			SYNTAX PSTIFMS1000DebugDACEntry
			MAX-ACCESS not-accessible
			STATUS current
			DESCRIPTION
				"Description."
			INDEX { pstIFMS1000DacTPortNum }
			::= { pstIFMS1000DebugDACTable 1 }

		
		PSTIFMS1000DebugDACEntry ::=
			SEQUENCE { 
				pstIFMS1000DacTPortNum
					Integer32,
				pstIFMS1000DacTChannelNum
					Integer32,
				pstIFMS1000TDacValue
					Integer32
			 }

		-- 1.3.6.1.4.1.48391.3.5.9.1.1
		pstIFMS1000DacTPortNum OBJECT-TYPE
			SYNTAX Integer32 (1..8)
			MAX-ACCESS read-only
			STATUS current
			DESCRIPTION
				"Description."
			::= { pstIFMS1000DebugDACEntry 1 }

		
		-- 1.3.6.1.4.1.48391.3.5.9.1.2
		pstIFMS1000DacTChannelNum OBJECT-TYPE
			SYNTAX Integer32
			MAX-ACCESS read-write
			STATUS current
			DESCRIPTION			" "
			::= { pstIFMS1000DebugDACEntry 2 }

		
		-- 1.3.6.1.4.1.48391.3.5.9.1.3
		pstIFMS1000TDacValue OBJECT-TYPE
			SYNTAX Integer32
			MAX-ACCESS read-write
			STATUS current
			DESCRIPTION			" "
			::= { pstIFMS1000DebugDACEntry 3 }

		
		-- 1.3.6.1.4.1.48391.3.5.10
		pstIFMS1000DebugE2promTable OBJECT-TYPE
			SYNTAX SEQUENCE OF PSTIFMS1000DebugE2promEntry
			MAX-ACCESS not-accessible
			STATUS current
			DESCRIPTION
				"Description."
			::= { pstIFMS1000 10 }

		
		-- 1.3.6.1.4.1.48391.3.5.10.1
		pstIFMS1000DebugE2promEntry OBJECT-TYPE
			SYNTAX PSTIFMS1000DebugE2promEntry
			MAX-ACCESS not-accessible
			STATUS current
			DESCRIPTION
				"Description."
			INDEX { pstIFMS1000DbE2TPortNum }
			::= { pstIFMS1000DebugE2promTable 1 }

		
		PSTIFMS1000DebugE2promEntry ::=
			SEQUENCE { 
				pstIFMS1000DbE2TPortNum
					Integer32,
				pstIFMS1000DbE2TAddr
					Integer32,
				pstIFMS1000DbE2TValue
					Integer32
			 }

		-- 1.3.6.1.4.1.48391.3.5.10.1.1
		pstIFMS1000DbE2TPortNum OBJECT-TYPE
			SYNTAX Integer32 (1..8)
			MAX-ACCESS read-only
			STATUS current
			DESCRIPTION
				"Description."
			::= { pstIFMS1000DebugE2promEntry 1 }

		
		-- 1.3.6.1.4.1.48391.3.5.10.1.2
		pstIFMS1000DbE2TAddr OBJECT-TYPE
			SYNTAX Integer32
			MAX-ACCESS read-write
			STATUS current
			DESCRIPTION			" "
			::= { pstIFMS1000DebugE2promEntry 2 }

		
		-- 1.3.6.1.4.1.48391.3.5.10.1.3
		pstIFMS1000DbE2TValue OBJECT-TYPE
			SYNTAX Integer32
			MAX-ACCESS read-write
			STATUS current
			DESCRIPTION			" "
			::= { pstIFMS1000DebugE2promEntry 3 }

		
		-- 1.3.6.1.4.1.48391.3.5.11
		pstIFMS1000SysConf OBJECT IDENTIFIER ::= { pstIFMS1000 11 }

		
		-- 1.3.6.1.4.1.48391.3.5.11.1
		pstIFMS1000BootMode OBJECT-TYPE
			SYNTAX Integer32
			MAX-ACCESS read-write
			STATUS current
			DESCRIPTION
				"Boot mode.
				Bit7-Bit0 are valid.Each bit indicates the settings of a port.
				0. Keep in idle after a power cycle or reboot.
				1. Keep last work status after a power cycle or reboot."
			::= { pstIFMS1000SysConf 1 }

		
		-- 1.3.6.1.4.1.48391.3.5.12
		pstIFMS1000ExtendAlarmTable OBJECT-TYPE
			SYNTAX SEQUENCE OF PSTIFMS1000ExtendAlarmEntry
			MAX-ACCESS not-accessible
			STATUS current
			DESCRIPTION
				"Description."
			::= { pstIFMS1000 12 }

		
		-- 1.3.6.1.4.1.48391.3.5.12.1
		pstIFMS1000ExtendAlarmEntry OBJECT-TYPE
			SYNTAX PSTIFMS1000ExtendAlarmEntry
			MAX-ACCESS not-accessible
			STATUS current
			DESCRIPTION
				"Description."
			INDEX { pstIFMS1000EAPortNum }
			::= { pstIFMS1000ExtendAlarmTable 1 }

		
		PSTIFMS1000ExtendAlarmEntry ::=
			SEQUENCE { 
				pstIFMS1000EAPortNum
					Integer32,
				pstIFMS1000ExtendAlarm
					Unsigned32
			 }

		-- 1.3.6.1.4.1.48391.3.5.12.1.1
		pstIFMS1000EAPortNum OBJECT-TYPE
			SYNTAX Integer32
			MAX-ACCESS read-only
			STATUS current
			DESCRIPTION
				"Description."
			::= { pstIFMS1000ExtendAlarmEntry 1 }

		
		-- 1.3.6.1.4.1.48391.3.5.12.1.2
		pstIFMS1000ExtendAlarm OBJECT-TYPE
			SYNTAX Unsigned32
			MAX-ACCESS read-write
			STATUS current
			DESCRIPTION
				"Indicates some alarms happen in FMS.
				Bit31-Bit24: Alarm Level. 0 is normal(green); 1 is critical(red); 2 is alarm(orange); 3 is warning(yellow).  
				Bit23-Bit0: The value of alarm type. The values list as below:
				1. A fault may occur but the system is unable to locate it.
				2. The reflectance at the far end is small, the fault detection under the fast scan mode may not be stable.
				Only the Alarm Level is not 0 means there is an alarm occurs.
				Set 0 will clear the alarm automately."
			::= { pstIFMS1000ExtendAlarmEntry 2 }

		
		-- 1.3.6.1.4.1.48391.3.5.13
		pstIFMS1000ExpertExtendTable OBJECT-TYPE
			SYNTAX SEQUENCE OF PSTIFMS1000ExpertExtendEntry
			MAX-ACCESS not-accessible
			STATUS current
			DESCRIPTION
				"Description."
			::= { pstIFMS1000 13 }

		
		-- 1.3.6.1.4.1.48391.3.5.13.1
		pstIFMS1000ExpertExtendEntry OBJECT-TYPE
			SYNTAX PSTIFMS1000ExpertExtendEntry
			MAX-ACCESS not-accessible
			STATUS current
			DESCRIPTION
				"Description."
			INDEX { pstIFMS1000EEPortNum }
			::= { pstIFMS1000ExpertExtendTable 1 }

		
		PSTIFMS1000ExpertExtendEntry ::=
			SEQUENCE { 
				pstIFMS1000EEPortNum
					Integer32,
				pstIFMS1000DgPBias1
					OCTET STRING,
				pstIFMS1000DgPBias2
					OCTET STRING,
				pstIFMS1000DgPModulation1
					OCTET STRING,
				pstIFMS1000DgPModulation2
					OCTET STRING,
				pstIFMS1000DgPBackScatter
					Integer32,
				pstIFMS1000DgPMeasureDeltaThld
					OCTET STRING,
				pstIFMS1000DgPCutPointThld
					OCTET STRING,
				pstIFMS1000DgPMFactor
					OCTET STRING,
				pstIFMS1000DgFaultCriticalThld
					OCTET STRING,
				pstIFMS1000DgFaultMajorThld
					OCTET STRING,
				pstIFMS1000DgFaultMinorThld
					OCTET STRING,
				pstIFMS1000DgPAFactor
					OCTET STRING,
				pstIFMS1000DgPBFactor
					OCTET STRING
			 }

		-- 1.3.6.1.4.1.48391.3.5.13.1.1
		pstIFMS1000EEPortNum OBJECT-TYPE
			SYNTAX Integer32 (1..8)
			MAX-ACCESS read-only
			STATUS current
			DESCRIPTION
				"Description."
			::= { pstIFMS1000ExpertExtendEntry 1 }

		
		-- 1.3.6.1.4.1.48391.3.5.13.1.2
		pstIFMS1000DgPBias1 OBJECT-TYPE
			SYNTAX OCTET STRING (SIZE (1..8))
			MAX-ACCESS read-write
			STATUS current
			DESCRIPTION
				"Description."
			::= { pstIFMS1000ExpertExtendEntry 2 }

		
		-- 1.3.6.1.4.1.48391.3.5.13.1.3
		pstIFMS1000DgPBias2 OBJECT-TYPE
			SYNTAX OCTET STRING (SIZE (1..8))
			MAX-ACCESS read-write
			STATUS current
			DESCRIPTION
				"Description."
			::= { pstIFMS1000ExpertExtendEntry 3 }

		
		-- 1.3.6.1.4.1.48391.3.5.13.1.4
		pstIFMS1000DgPModulation1 OBJECT-TYPE
			SYNTAX OCTET STRING (SIZE (1..8))
			MAX-ACCESS read-write
			STATUS current
			DESCRIPTION
				"Description."
			::= { pstIFMS1000ExpertExtendEntry 4 }

		
		-- 1.3.6.1.4.1.48391.3.5.13.1.5
		pstIFMS1000DgPModulation2 OBJECT-TYPE
			SYNTAX OCTET STRING (SIZE (1..8))
			MAX-ACCESS read-write
			STATUS current
			DESCRIPTION
				"Description."
			::= { pstIFMS1000ExpertExtendEntry 5 }

		
		-- 1.3.6.1.4.1.48391.3.5.13.1.6
		pstIFMS1000DgPBackScatter OBJECT-TYPE
			SYNTAX Integer32
			MAX-ACCESS read-write
			STATUS current
			DESCRIPTION
				"Description."
			::= { pstIFMS1000ExpertExtendEntry 6 }

		
		-- 1.3.6.1.4.1.48391.3.5.13.1.7
		pstIFMS1000DgPMeasureDeltaThld OBJECT-TYPE
			SYNTAX OCTET STRING (SIZE (1..32))
			MAX-ACCESS read-write
			STATUS current
			DESCRIPTION
				"The delta threshold in POTDR measurement. It should be a float value."
			::= { pstIFMS1000ExpertExtendEntry 7 }

		
		-- 1.3.6.1.4.1.48391.3.5.13.1.8
		pstIFMS1000DgPCutPointThld OBJECT-TYPE
			SYNTAX OCTET STRING (SIZE (1..32))
			MAX-ACCESS read-write
			STATUS current
			DESCRIPTION
				"Description."
			::= { pstIFMS1000ExpertExtendEntry 8 }

		
		-- 1.3.6.1.4.1.48391.3.5.13.1.9
		pstIFMS1000DgPMFactor OBJECT-TYPE
			SYNTAX OCTET STRING (SIZE (1..32))
			MAX-ACCESS read-write
			STATUS current
			DESCRIPTION
				"Description."
			::= { pstIFMS1000ExpertExtendEntry 9 }

		
		-- 1.3.6.1.4.1.48391.3.5.13.1.10
		pstIFMS1000DgFaultCriticalThld OBJECT-TYPE
			SYNTAX OCTET STRING (SIZE (1..32))
			MAX-ACCESS read-write
			STATUS current
			DESCRIPTION
				"Description."
			::= { pstIFMS1000ExpertExtendEntry 10 }

		
		-- 1.3.6.1.4.1.48391.3.5.13.1.11
		pstIFMS1000DgFaultMajorThld OBJECT-TYPE
			SYNTAX OCTET STRING (SIZE (1..32))
			MAX-ACCESS read-write
			STATUS current
			DESCRIPTION
				"Description."
			::= { pstIFMS1000ExpertExtendEntry 11 }

		
		-- 1.3.6.1.4.1.48391.3.5.13.1.12
		pstIFMS1000DgFaultMinorThld OBJECT-TYPE
			SYNTAX OCTET STRING (SIZE (1..32))
			MAX-ACCESS read-write
			STATUS current
			DESCRIPTION
				"Description."
			::= { pstIFMS1000ExpertExtendEntry 12 }

		
		-- 1.3.6.1.4.1.48391.3.5.13.1.13
		pstIFMS1000DgPAFactor OBJECT-TYPE
			SYNTAX OCTET STRING (SIZE (1..32))
			MAX-ACCESS read-write
			STATUS current
			DESCRIPTION
				"Description."
			::= { pstIFMS1000ExpertExtendEntry 13 }

		
		-- 1.3.6.1.4.1.48391.3.5.13.1.14
		pstIFMS1000DgPBFactor OBJECT-TYPE
			SYNTAX OCTET STRING (SIZE (1..32))
			MAX-ACCESS read-write
			STATUS current
			DESCRIPTION
				"Description."
			::= { pstIFMS1000ExpertExtendEntry 14 }

		
		-- 1.3.6.1.4.1.48391.3.5.14
		pstIFMS1000PonConfTable OBJECT-TYPE
			SYNTAX SEQUENCE OF PSTIFMS1000PonConfEntry
			MAX-ACCESS not-accessible
			STATUS current
			DESCRIPTION
				"Description."
			::= { pstIFMS1000 14 }

		
		-- 1.3.6.1.4.1.48391.3.5.14.1
		pstIFMS1000PonConfEntry OBJECT-TYPE
			SYNTAX PSTIFMS1000PonConfEntry
			MAX-ACCESS not-accessible
			STATUS current
			DESCRIPTION
				"Description."
			INDEX { pctPortNum }
			::= { pstIFMS1000PonConfTable 1 }

		
		PSTIFMS1000PonConfEntry ::=
			SEQUENCE { 
				pctPortNum
					Unsigned32,
				pctSp1LocItem
					Unsigned32
			 }

		-- 1.3.6.1.4.1.48391.3.5.14.1.1
		pctPortNum OBJECT-TYPE
			SYNTAX Unsigned32
			MAX-ACCESS read-only
			STATUS current
			DESCRIPTION
				"Description."
			::= { pstIFMS1000PonConfEntry 1 }

		
		-- 1.3.6.1.4.1.48391.3.5.14.1.2
		pctSp1LocItem OBJECT-TYPE
			SYNTAX Unsigned32
			MAX-ACCESS read-write
			STATUS current
			DESCRIPTION
				"Indicates which point in the finger print is attached with PON's splitter 1.
				0 means no valid attachment."
			::= { pstIFMS1000PonConfEntry 2 }

		
		-- 1.3.6.1.4.1.48391.3.5.15
		pstIFMS1000ParamsV32 OBJECT IDENTIFIER ::= { pstIFMS1000 15 }

		
		-- 1.3.6.1.4.1.48391.3.5.15.1
		pstIFMS1000ParamsV32TotalNumTable OBJECT-TYPE
			SYNTAX SEQUENCE OF PSTIFMS1000ParamsV32TotalNumEntry
			MAX-ACCESS not-accessible
			STATUS current
			DESCRIPTION
				"Description."
			::= { pstIFMS1000ParamsV32 1 }

		
		-- 1.3.6.1.4.1.48391.3.5.15.1.1
		pstIFMS1000ParamsV32TotalNumEntry OBJECT-TYPE
			SYNTAX PSTIFMS1000ParamsV32TotalNumEntry
			MAX-ACCESS not-accessible
			STATUS current
			DESCRIPTION
				"Description."
			INDEX { v32TPortNum }
			::= { pstIFMS1000ParamsV32TotalNumTable 1 }

		
		PSTIFMS1000ParamsV32TotalNumEntry ::=
			SEQUENCE { 
				v32TPortNum
					Integer32,
				v32PortTotalNum
					Integer32
			 }

		-- 1.3.6.1.4.1.48391.3.5.15.1.1.1
		v32TPortNum OBJECT-TYPE
			SYNTAX Integer32 (1..8)
			MAX-ACCESS read-only
			STATUS current
			DESCRIPTION
				"Description."
			::= { pstIFMS1000ParamsV32TotalNumEntry 1 }

		
		-- 1.3.6.1.4.1.48391.3.5.15.1.1.2
		v32PortTotalNum OBJECT-TYPE
			SYNTAX Integer32
			MAX-ACCESS read-only
			STATUS current
			DESCRIPTION
				"Indicates the total number of v32 parameters"
			::= { pstIFMS1000ParamsV32TotalNumEntry 2 }

		
		-- 1.3.6.1.4.1.48391.3.5.15.2
		pstIFMS1000ParamsV32NameTable OBJECT-TYPE
			SYNTAX SEQUENCE OF PSTIFMS1000ParamsV32NameEntry
			MAX-ACCESS not-accessible
			STATUS current
			DESCRIPTION
				"Description."
			::= { pstIFMS1000ParamsV32 2 }

		
		-- 1.3.6.1.4.1.48391.3.5.15.2.1
		pstIFMS1000ParamsV32NameEntry OBJECT-TYPE
			SYNTAX PSTIFMS1000ParamsV32NameEntry
			MAX-ACCESS not-accessible
			STATUS current
			DESCRIPTION
				"Description."
			INDEX { v32PortNum, v32ParamNameNum }
			::= { pstIFMS1000ParamsV32NameTable 1 }

		
		PSTIFMS1000ParamsV32NameEntry ::=
			SEQUENCE { 
				v32PortNum
					Integer32,
				v32ParamNameNum
					Integer32,
				v32ParamName
					OCTET STRING
			 }

		-- 1.3.6.1.4.1.48391.3.5.15.2.1.1
		v32PortNum OBJECT-TYPE
			SYNTAX Integer32 (1..8)
			MAX-ACCESS read-only
			STATUS current
			DESCRIPTION
				"Description."
			::= { pstIFMS1000ParamsV32NameEntry 1 }

		
		-- 1.3.6.1.4.1.48391.3.5.15.2.1.2
		v32ParamNameNum OBJECT-TYPE
			SYNTAX Integer32
			MAX-ACCESS read-only
			STATUS current
			DESCRIPTION
				"The range is 1 to v32PortTotalNum"
			::= { pstIFMS1000ParamsV32NameEntry 2 }

		
		-- 1.3.6.1.4.1.48391.3.5.15.2.1.3
		v32ParamName OBJECT-TYPE
			SYNTAX OCTET STRING (SIZE (1..32))
			MAX-ACCESS read-only
			STATUS current
			DESCRIPTION
				"Description."
			::= { pstIFMS1000ParamsV32NameEntry 3 }

		
		-- 1.3.6.1.4.1.48391.3.5.15.3
		pstIFMS1000ParamsV32ValTable OBJECT-TYPE
			SYNTAX SEQUENCE OF PSTIFMS1000ParamsV32ValEntry
			MAX-ACCESS not-accessible
			STATUS current
			DESCRIPTION
				"Description."
			::= { pstIFMS1000ParamsV32 3 }

		
		-- 1.3.6.1.4.1.48391.3.5.15.3.1
		pstIFMS1000ParamsV32ValEntry OBJECT-TYPE
			SYNTAX PSTIFMS1000ParamsV32ValEntry
			MAX-ACCESS not-accessible
			STATUS current
			DESCRIPTION
				"Description."
			INDEX { v32ValPortNum, v32ParamValNum }
			::= { pstIFMS1000ParamsV32ValTable 1 }

		
		PSTIFMS1000ParamsV32ValEntry ::=
			SEQUENCE { 
				v32ValPortNum
					Integer32,
				v32ParamValNum
					Integer32,
				v32ParamVal
					Unsigned32
			 }

		-- 1.3.6.1.4.1.48391.3.5.15.3.1.1
		v32ValPortNum OBJECT-TYPE
			SYNTAX Integer32 (1..8)
			MAX-ACCESS read-only
			STATUS current
			DESCRIPTION
				"Description."
			::= { pstIFMS1000ParamsV32ValEntry 1 }

		
		-- 1.3.6.1.4.1.48391.3.5.15.3.1.2
		v32ParamValNum OBJECT-TYPE
			SYNTAX Integer32
			MAX-ACCESS read-only
			STATUS current
			DESCRIPTION
				"The range is 1 to v32PortTotalNum"
			::= { pstIFMS1000ParamsV32ValEntry 2 }

		
		-- 1.3.6.1.4.1.48391.3.5.15.3.1.3
		v32ParamVal OBJECT-TYPE
			SYNTAX Unsigned32
			MAX-ACCESS read-write
			STATUS current
			DESCRIPTION
				"Description."
			::= { pstIFMS1000ParamsV32ValEntry 3 }

		
		-- 1.3.6.1.4.1.48391.3.5.16
		pstIFMS1000ParamsS32 OBJECT IDENTIFIER ::= { pstIFMS1000 16 }

		
		-- 1.3.6.1.4.1.48391.3.5.16.1
		pstIFMS1000ParamsS32TotalNumTable OBJECT-TYPE
			SYNTAX SEQUENCE OF PSTIFMS1000ParamsS32TotalNumEntry
			MAX-ACCESS not-accessible
			STATUS current
			DESCRIPTION
				"Description."
			::= { pstIFMS1000ParamsS32 1 }

		
		-- 1.3.6.1.4.1.48391.3.5.16.1.1
		pstIFMS1000ParamsS32TotalNumEntry OBJECT-TYPE
			SYNTAX PSTIFMS1000ParamsS32TotalNumEntry
			MAX-ACCESS not-accessible
			STATUS current
			DESCRIPTION
				"Description."
			INDEX { s32TPortNum }
			::= { pstIFMS1000ParamsS32TotalNumTable 1 }

		
		PSTIFMS1000ParamsS32TotalNumEntry ::=
			SEQUENCE { 
				s32TPortNum
					Integer32,
				s32PortTotalNum
					Integer32
			 }

		-- 1.3.6.1.4.1.48391.3.5.16.1.1.1
		s32TPortNum OBJECT-TYPE
			SYNTAX Integer32 (1..8)
			MAX-ACCESS read-only
			STATUS current
			DESCRIPTION
				"Description."
			::= { pstIFMS1000ParamsS32TotalNumEntry 1 }

		
		-- 1.3.6.1.4.1.48391.3.5.16.1.1.2
		s32PortTotalNum OBJECT-TYPE
			SYNTAX Integer32
			MAX-ACCESS read-only
			STATUS current
			DESCRIPTION
				"Indicates the total number of s32 parameters"
			::= { pstIFMS1000ParamsS32TotalNumEntry 2 }

		
		-- 1.3.6.1.4.1.48391.3.5.16.2
		pstIFMS1000ParamsS32NameTable OBJECT-TYPE
			SYNTAX SEQUENCE OF PSTIFMS1000ParamsS32NameEntry
			MAX-ACCESS not-accessible
			STATUS current
			DESCRIPTION
				"Description."
			::= { pstIFMS1000ParamsS32 2 }

		
		-- 1.3.6.1.4.1.48391.3.5.16.2.1
		pstIFMS1000ParamsS32NameEntry OBJECT-TYPE
			SYNTAX PSTIFMS1000ParamsS32NameEntry
			MAX-ACCESS not-accessible
			STATUS current
			DESCRIPTION
				"Description."
			INDEX { s32PortNum, s32ParamNameNum }
			::= { pstIFMS1000ParamsS32NameTable 1 }

		
		PSTIFMS1000ParamsS32NameEntry ::=
			SEQUENCE { 
				s32PortNum
					Integer32,
				s32ParamNameNum
					Integer32,
				s32ParamNameVal
					OCTET STRING
			 }

		-- 1.3.6.1.4.1.48391.3.5.16.2.1.1
		s32PortNum OBJECT-TYPE
			SYNTAX Integer32 (1..8)
			MAX-ACCESS read-only
			STATUS current
			DESCRIPTION
				"Description."
			::= { pstIFMS1000ParamsS32NameEntry 1 }

		
		-- 1.3.6.1.4.1.48391.3.5.16.2.1.2
		s32ParamNameNum OBJECT-TYPE
			SYNTAX Integer32
			MAX-ACCESS read-only
			STATUS current
			DESCRIPTION
				"The range is 1 to s32PortTotalNum"
			::= { pstIFMS1000ParamsS32NameEntry 2 }

		
		-- 1.3.6.1.4.1.48391.3.5.16.2.1.3
		s32ParamNameVal OBJECT-TYPE
			SYNTAX OCTET STRING (SIZE (1..32))
			MAX-ACCESS read-only
			STATUS current
			DESCRIPTION
				"Description."
			::= { pstIFMS1000ParamsS32NameEntry 3 }

		
		-- 1.3.6.1.4.1.48391.3.5.16.3
		pstIFMS1000ParamsS32ValTable OBJECT-TYPE
			SYNTAX SEQUENCE OF PSTIFMS1000ParamsS32ValEntry
			MAX-ACCESS not-accessible
			STATUS current
			DESCRIPTION
				"Description."
			::= { pstIFMS1000ParamsS32 3 }

		
		-- 1.3.6.1.4.1.48391.3.5.16.3.1
		pstIFMS1000ParamsS32ValEntry OBJECT-TYPE
			SYNTAX PSTIFMS1000ParamsS32ValEntry
			MAX-ACCESS not-accessible
			STATUS current
			DESCRIPTION
				"Description."
			INDEX { s32ValPortNum, s32ParamValNum }
			::= { pstIFMS1000ParamsS32ValTable 1 }

		
		PSTIFMS1000ParamsS32ValEntry ::=
			SEQUENCE { 
				s32ValPortNum
					Integer32,
				s32ParamValNum
					Integer32,
				s32ParamVal
					OCTET STRING
			 }

		-- 1.3.6.1.4.1.48391.3.5.16.3.1.1
		s32ValPortNum OBJECT-TYPE
			SYNTAX Integer32 (1..8)
			MAX-ACCESS read-only
			STATUS current
			DESCRIPTION
				"Description."
			::= { pstIFMS1000ParamsS32ValEntry 1 }

		
		-- 1.3.6.1.4.1.48391.3.5.16.3.1.2
		s32ParamValNum OBJECT-TYPE
			SYNTAX Integer32
			MAX-ACCESS read-only
			STATUS current
			DESCRIPTION
				"The range is 1 to s32PortTotalNum"
			::= { pstIFMS1000ParamsS32ValEntry 2 }

		
		-- 1.3.6.1.4.1.48391.3.5.16.3.1.3
		s32ParamVal OBJECT-TYPE
			SYNTAX OCTET STRING (SIZE (1..32))
			MAX-ACCESS read-write
			STATUS current
			DESCRIPTION
				"Description."
			::= { pstIFMS1000ParamsS32ValEntry 3 }

		
		-- 1.3.6.1.4.1.48391.3.5.17
		pstIFMS1000SwitchInfo OBJECT IDENTIFIER ::= { pstIFMS1000 17 }

		
		-- 1.3.6.1.4.1.48391.3.5.17.1
		pstIFMS1000SwitchModuleNum OBJECT-TYPE
			SYNTAX Integer32
			MAX-ACCESS read-only
			STATUS current
			DESCRIPTION
				"Indicates which module number the switch is installed.
				0. No switch module inside.
				1-4. The switch module's number.
				255. External switch attached. You may get the details in 'pstIFMS1000ExternalSwitchInfo'"
			::= { pstIFMS1000SwitchInfo 1 }

		
		-- 1.3.6.1.4.1.48391.3.5.17.2
		pstIFMS1000SwitchInterval OBJECT-TYPE
			SYNTAX Integer32
			UNITS "Second"
			MAX-ACCESS read-write
			STATUS current
			DESCRIPTION
				"Indicates the switch delay between two port switching.
				The unit is second.
				This field is only valid when SwitchModuleNum is not zero."
			::= { pstIFMS1000SwitchInfo 2 }

		
		-- 1.3.6.1.4.1.48391.3.5.17.3
		pstIFMS1000SwitchCurrentPort OBJECT-TYPE
			SYNTAX Integer32
			MAX-ACCESS read-only
			STATUS current
			DESCRIPTION
				"Indicates current running port which is switched into."
			::= { pstIFMS1000SwitchInfo 3 }

		
		-- 1.3.6.1.4.1.48391.3.5.18
		pstIFMS1000ExternalSwitchInfo OBJECT IDENTIFIER ::= { pstIFMS1000 18 }

		
		-- 1.3.6.1.4.1.48391.3.5.18.1
		pstIFMS1000ExtSwitchAttType OBJECT-TYPE
			SYNTAX Integer32
			MAX-ACCESS read-write
			STATUS current
			DESCRIPTION
				"Indicates current external switch type.
				0. No external switch is attached.
				1. 1*8 Switch Type 1.
				2. 1*16 Switch Type 1.
				3. 1*24 Switch Type 1."
			::= { pstIFMS1000ExternalSwitchInfo 1 }

		
		-- 1.3.6.1.4.1.48391.3.5.18.2
		pstIFMS1000ExtSwitchAttachPort OBJECT-TYPE
			SYNTAX Integer32
			MAX-ACCESS read-write
			STATUS current
			DESCRIPTION
				"The 3030's port number which is attached the external switch."
			::= { pstIFMS1000ExternalSwitchInfo 2 }

		
		-- 1.3.6.1.4.1.48391.3.5.18.3
		pstIFMS1000ExtSwitchConnType OBJECT-TYPE
			SYNTAX Integer32
			MAX-ACCESS read-write
			STATUS current
			DESCRIPTION
				"0. N/A
				1. Ethernet
				2. UART"
			::= { pstIFMS1000ExternalSwitchInfo 3 }

		
		-- 1.3.6.1.4.1.48391.3.5.18.4
		pstIFMS1000ExtSwitchIpAddr OBJECT-TYPE
			SYNTAX IpAddress
			MAX-ACCESS read-write
			STATUS current
			DESCRIPTION
				"Ip address of external switch."
			::= { pstIFMS1000ExternalSwitchInfo 4 }

		
		-- 1.3.6.1.4.1.48391.3.5.18.5
		pstIFMS1000ExtSwitchIpPort OBJECT-TYPE
			SYNTAX Integer32
			MAX-ACCESS read-write
			STATUS current
			DESCRIPTION
				"Tcp port of external switch."
			::= { pstIFMS1000ExternalSwitchInfo 5 }

		
		-- 1.3.6.1.4.1.48391.3.5.18.6
		pstIFMS1000ExtSwitchUartBaud OBJECT-TYPE
			SYNTAX Integer32
			MAX-ACCESS read-write
			STATUS current
			DESCRIPTION
				"Baud rate when using UART to connect to external switch."
			::= { pstIFMS1000ExternalSwitchInfo 6 }

		
		-- 1.3.6.1.4.1.48391.3.5.18.7
		pstIFMS1000ExtSwitchTotalSwitchNum OBJECT-TYPE
			SYNTAX Integer32
			MAX-ACCESS read-only
			STATUS current
			DESCRIPTION
				"Indicates how many ports the external switch has."
			::= { pstIFMS1000ExternalSwitchInfo 7 }

		
		-- 1.3.6.1.4.1.48391.3.5.18.8
		pstIFMS1000ExtSwitchCurrentNum OBJECT-TYPE
			SYNTAX Integer32
			MAX-ACCESS read-only
			STATUS current
			DESCRIPTION
				"Indicates current port number which external switch is switched in.
				"
			::= { pstIFMS1000ExternalSwitchInfo 8 }

		
		-- 1.3.6.1.4.1.48391.3.5.18.9
		pstIFMS1000ExtSwitchStatus OBJECT-TYPE
			SYNTAX Integer32
			MAX-ACCESS read-only
			STATUS current
			DESCRIPTION
				"Indicates current connection status of external switch.
				0. Failed to connect or control.
				1. Connected.
				"
			::= { pstIFMS1000ExternalSwitchInfo 9 }

		
	
	END

--
-- PST-IFMS1000-MIB.my
--
